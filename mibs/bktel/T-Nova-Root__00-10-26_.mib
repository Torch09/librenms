--***********************************************************
-- 17.11.03 Heldmann, BKtel, Removed german language descriptions
--***********************************************************

-- **************************************************************
-- T-NOVA-ROOT-MIB
--
-- Revision Notes:
-- 06.10.00  Klaus Biedenbach, T-Nova, E531i
-- 				erster Entwurf
--				OID für tnova ist noch in Vorbereitung
-- 26.10.00  Klaus Biedenbach, T-Nova, E531i
--				OID für T-Nova eingetragen, Syntaxfehler korrigiert
-- **************************************************************

T-NOVA-ROOT-MIB DEFINITIONS ::= BEGIN

IMPORTS
	enterprises		FROM RFC1155-SMI;

tnova					OBJECT IDENTIFIER ::= { enterprises 7311 }
	commonTrapControl 		OBJECT IDENTIFIER ::= { tnova 1 }
	commonInventory 		OBJECT IDENTIFIER ::= { tnova 2 }
	hfc					OBJECT IDENTIFIER ::= { tnova 20 }

END
