-- ****************************************************************************
-- *
-- * Module Name: HMS072R5.MIB (SCTE 37)
-- *
-- * SCTE Status: ADOPTED JANUARY 11, 2002
-- *  
-- * This MIB provides the branch object identifiers 
-- * for each of the MIBs with in the SCTE HMS Tree
-- * 
-- ****************************************************************************

SCTE-HMS-ROOTS DEFINITIONS ::= BEGIN

IMPORTS
     scteHmsTree
          FROM SCTE-ROOT  -- see HMS028 (SCTE 36)
;

propertyIdent OBJECT IDENTIFIER ::= { scteHmsTree 1}

--     DESCRIPTION
--     "Defines the base OID of the property MIB"
--     "SCTE-HMS-PROPERTY-MIB is defined by HMS026 (SCTE 38-1)"

alarmsIdent   OBJECT IDENTIFIER ::= { scteHmsTree 2}

--     DESCRIPTION
--     "Defines the base OID of the Alarms MIB"
--     "SCTE-HMS-ALARMS-MIB is defined by HMS023  (SCTE 38-2)"

commonIdent   OBJECT IDENTIFIER ::= { scteHmsTree 3}

--     DESCRIPTION
--     "Defines the base OID of the Common MIB"
--     "SCTE-HMS-COMMON-MIB is defined by HMS024  (SCTE 38-3)"

psIdent       OBJECT IDENTIFIER ::= { scteHmsTree 4}

--     DESCRIPTION
--     "Defines the base OID of the Power Supply MIB"
--     "SCTE-HMS-PS-MIB is defined by HMS027 (SCTE 38-4)"

fnIdent       OBJECT IDENTIFIER ::= { scteHmsTree 5}

--     DESCRIPTION
--     "Defines the base OID of the Fiber Node MIB"
--     "SCTE-HMS-FIBERNODE-MIB is defined by HMS025 (SCTE 38-5)"

genIdent      OBJECT IDENTIFIER ::= { scteHmsTree 6}

--     DESCRIPTION
--     "Defines the base OID of the Generator MIB"
--     "SCTE-HMS-GEN-MIB is defined by HMS033 (SCTE 38-6)"

transponderInterfaceBusIdent  OBJECT IDENTIFIER ::= { scteHmsTree 7}

--     DESCRIPTION
--     "Defines the base OID of the Transponder Interface Bus MIB"
--     "SCTE-HMS-TIB-MIB is defined by HMS050 (SCTE 38-7)"

downloadIdent    OBJECT IDENTIFIER ::= { scteHmsTree 8}

--     DESCRIPTION
--     "Defines the base OID of the Download MIB"
--     "SCTE-HMS-DOWNLOAD-MIB is defined by HMS063 (SCTE 38-8)"

oaIdent OBJECT IDENTIFIER ::= { scteHmsTree 9}

--     DESCRIPTION
--     "Defines the base OID of the Optical Amplifier MIB"
--     "SCTE-HMS-OPTICALAMP-MIB is defined by HMS082 (SCTE 38-9)"

-- ****************************** Inserted M.Heldmann for test-only
opIdent OBJECT IDENTIFIER ::= { scteHmsTree 20}
headEndIdent OBJECT IDENTIFIER ::= { scteHmsTree 21}
rfAmpIdent OBJECT IDENTIFIER ::= { scteHmsTree 22}
	   

END
