--- ****************************************************************************
-- *
-- * Description:   Implements definitions for the BFE module
-- *                RF Frequency Equalizer
-- *
-- * Copyright 2010 by BKtel communications GmbH
-- *
-- *
-- *     V.0.1 17.08.2010  M. Heldmann    first draft
-- *     V.0.2 11.07.2013  M. Heldmann    adjusted syntax of "CommonEntry" to remove MIB compiler warnings
-- *     V.0.3 05.09.2014  M. Heldmann    changed CommonModuleWidth and ConfigNESlotWrite STATUS to optional
-- ****************************************************************************

BKTEL-HFC862-BFE-V01-MIB DEFINITIONS ::= BEGIN

    IMPORTS
        experimental, enterprises, TimeTicks, IpAddress, Counter
                 FROM RFC1155-SMI
    OBJECT-TYPE
                 FROM RFC-1212
        TRAP-TYPE
                 FROM RFC-1215
        modules, DisplayString, TruthValue, PerceivedSeverityValue, NESlotValue, ModuleWidthValue
                 FROM   BKTEL-HFC862-BASE-MIB
    ;

    bfe                 OBJECT IDENTIFIER ::= { modules 120 }
    bfeCommon           OBJECT IDENTIFIER ::= { bfe 1 }
    bfeStates           OBJECT IDENTIFIER ::= { bfe 2 }
    bfeConfiguration    OBJECT IDENTIFIER ::= { bfe 3 }
    bfeControl          OBJECT IDENTIFIER ::= { bfe 4 }
    bfeMeasuringValues  OBJECT IDENTIFIER ::= { bfe 5 }
    bfeDisplay          OBJECT IDENTIFIER ::= { bfe 6 }


--
-- Type definitions
--

    RfMode ::= INTEGER
        {
        modeNormal(1),
        modeLowNoise(2),
        modeLowDistortion(3)
        }

    RedundancyMode ::= INTEGER
        {
        modeForceStandby(1),
        modeAlwaysActive(2),
        -- the following modes are only supported if otxdDisplayRedundancySupported == true(1)
        modeNominalMaster(3),
        modeRedundantSlave(4),
        modeNominalRedundantAutomaticBySlot(5)
        }

--  RedundancyMask ::= INTEGER
--      {
--      maskAlarmsOnly(1),
--      maskAlarmsAndWarnings(2),
--      maskSpecialAdjusted(3)           -- This item is NOT writable !!
--      }

    DeviceRedundancyState ::= INTEGER
        {
        stateNominalMaster(1),
        stateRedundantSlave(2)
        }

    DeviceActivityState ::= INTEGER
        {
        standby(1),
        active(2)
        }

    NESlotWriteValue ::= INTEGER (-1..99)


-- MibCompiler defs --
-- $idx$: InternalVoltage
-- $idx$: Equalizer
-- MibCompiler defs --


--*****************************************************************************************
-- bfeCommon group

    bfeCommonNumberOfModules OBJECT-TYPE
        SYNTAX  INTEGER(0..50)
        ACCESS  read-only
        STATUS  mandatory
        DESCRIPTION "Number of modules in table."
  ::= { bfeCommon 1 }

    bfeCommonTable OBJECT-TYPE
        SYNTAX SEQUENCE OF BfeCommonEntry
        ACCESS not-accessible
        STATUS mandatory
        DESCRIPTION "The table contains all modules of the BFE-type in the NE"
  ::= { bfeCommon 2 }

-- table of states entry(ro/rw)

    bfeCommonEntry OBJECT-TYPE
        SYNTAX BfeCommonEntry
        ACCESS not-accessible
        STATUS mandatory
        DESCRIPTION "Common-Values for a module."
        INDEX { bfeNESlot }
  ::= { bfeCommonTable 1 }

-- the structure of the entry

    BfeCommonEntry ::= SEQUENCE
    {
        bfeNESlot                      NESlotValue,
        bfeCommonType                  DisplayString,
        bfeCommonDescr                 DisplayString,
        bfeCommonFirmwareId            DisplayString,
        bfeCommonModuleWidth           ModuleWidthValue
    }

    bfeNESlot OBJECT-TYPE
        SYNTAX  NESlotValue
        ACCESS  read-only
        STATUS  mandatory
        DESCRIPTION
        "The slot number of the chassis for which this
        entry contains management information."
    ::= { bfeCommonEntry 1 }

    bfeCommonType OBJECT-TYPE
        SYNTAX  DisplayString  (SIZE(0..32))
        ACCESS  read-only
        STATUS  mandatory
        DESCRIPTION
        "The type of physical module. modSlotEmpty indicates
         an empty slot.  A Value of modSlotUnknown indicates
         that the type of module is unknown."
    ::= { bfeCommonEntry 2 }

    bfeCommonDescr OBJECT-TYPE
        SYNTAX  DisplayString
        ACCESS  read-write
        STATUS  mandatory
        DESCRIPTION
        "A textual description of the module.
        If not available, this Value should be
        set to a zero length string."
    ::= { bfeCommonEntry 3 }

    bfeCommonFirmwareId OBJECT-TYPE
        SYNTAX DisplayString (SIZE(0..32))
        ACCESS read-only
        STATUS mandatory
        DESCRIPTION "The firmware Id of the module."
    ::= { bfeCommonEntry 4 }

    bfeCommonModuleWidth OBJECT-TYPE
        SYNTAX ModuleWidthValue
        ACCESS read-only
        STATUS optional
        DESCRIPTION "The width of the module in multiples of slots (1, 2, ...)"
    ::= { bfeCommonEntry 5 }

--*****************************************************************************************
-- bfeMeasuringValues group

-- table of measuring Values

    bfeMeasuringValuesTable OBJECT-TYPE
        SYNTAX SEQUENCE OF BfeMeasuringValuesEntry
        ACCESS not-accessible
        STATUS mandatory
        DESCRIPTION ""
   ::= { bfeMeasuringValues 1 }

-- table of measuring Values entry

    bfeMeasuringValuesEntry OBJECT-TYPE
        SYNTAX BfeMeasuringValuesEntry
        ACCESS not-accessible
        STATUS mandatory
        DESCRIPTION "Common-Values for a module."
        INDEX { bfeNESlot }
  ::= { bfeMeasuringValuesTable 1 }

--  the structure of the entry

    BfeMeasuringValuesEntry ::= SEQUENCE
    {
        bfeTemperatureLoLo             INTEGER,
        bfeTemperatureLo               INTEGER,
        bfeTemperatureValue            INTEGER,
        bfeTemperatureHi               INTEGER,
        bfeTemperatureHiHi             INTEGER,

        bfeRfOutputPowerLoLo           INTEGER,
        bfeRfOutputPowerLo             INTEGER,
        bfeRfOutputPowerValue          INTEGER,
        bfeRfOutputPowerHi             INTEGER,
        bfeRfOutputPowerHiHi           INTEGER,

        bfeInputVoltageLoLo            INTEGER,
        bfeInputVoltageLo              INTEGER,
        bfeInputVoltageValue           INTEGER,
        bfeInputVoltageHi              INTEGER,
        bfeInputVoltageHiHi            INTEGER,

        bfeInternalVoltage1LoLo        INTEGER,
        bfeInternalVoltage1Lo          INTEGER,
        bfeInternalVoltage1Value       INTEGER,
        bfeInternalVoltage1Hi          INTEGER,
        bfeInternalVoltage1HiHi        INTEGER,
                                          
        bfeInternalVoltage2LoLo        INTEGER,
        bfeInternalVoltage2Lo          INTEGER,
        bfeInternalVoltage2Value       INTEGER,
        bfeInternalVoltage2Hi          INTEGER,
        bfeInternalVoltage2HiHi        INTEGER,
                                          
        bfeInternalVoltage3LoLo        INTEGER,
        bfeInternalVoltage3Lo          INTEGER,
        bfeInternalVoltage3Value       INTEGER,
        bfeInternalVoltage3Hi          INTEGER,
        bfeInternalVoltage3HiHi        INTEGER
    }

-- *****
    bfeTemperatureLoLo OBJECT-TYPE
        SYNTAX INTEGER
        ACCESS read-only
        STATUS mandatory
        DESCRIPTION "Device temperature low alarm threshold in 0.1 celsius degrees."
    ::= { bfeMeasuringValuesEntry 1 }

    bfeTemperatureLo OBJECT-TYPE
        SYNTAX INTEGER
        ACCESS read-only
        STATUS mandatory
        DESCRIPTION "Device temperature low warning threshold in 0.1 celsius degrees."
    ::= { bfeMeasuringValuesEntry 2 }

    bfeTemperatureValue OBJECT-TYPE
        SYNTAX INTEGER
        ACCESS read-only
        STATUS mandatory
        DESCRIPTION "Device temperature in 0.1 celsius degrees."
    ::= { bfeMeasuringValuesEntry 3 }

    bfeTemperatureHi OBJECT-TYPE
        SYNTAX INTEGER
        ACCESS read-only
        STATUS mandatory
        DESCRIPTION "Device temperature high warning threshold in 0.1 celsius degrees."
    ::= { bfeMeasuringValuesEntry 4 }

    bfeTemperatureHiHi OBJECT-TYPE
        SYNTAX INTEGER
        ACCESS read-only
        STATUS mandatory
        DESCRIPTION "Device temperature high alarm threshold in 0.1 celsius degrees."
    ::= { bfeMeasuringValuesEntry 5 }

-- *****
    bfeRfOutputPowerLoLo OBJECT-TYPE
        SYNTAX INTEGER
        ACCESS read-only
        STATUS mandatory
        DESCRIPTION "RF output power (total rms) low alarm threshold in steps of 0.1 dBm."
    ::= { bfeMeasuringValuesEntry 6 }

    bfeRfOutputPowerLo OBJECT-TYPE
        SYNTAX INTEGER
        ACCESS read-only
        STATUS mandatory
        DESCRIPTION "RF output power (total rms) low warning threshold in steps of 0.1 dBm."
    ::= { bfeMeasuringValuesEntry 7 }

    bfeRfOutputPowerValue OBJECT-TYPE
        SYNTAX INTEGER
        ACCESS read-only
        STATUS mandatory
        DESCRIPTION "RF output power (total rms) in steps of 0.1 dBm."
    ::= { bfeMeasuringValuesEntry 8 }

    bfeRfOutputPowerHi OBJECT-TYPE
        SYNTAX INTEGER
        ACCESS read-only
        STATUS mandatory
        DESCRIPTION "RF output power (total rms) high warning threshold in steps of 0.1 dBm."
    ::= { bfeMeasuringValuesEntry 9 }

    bfeRfOutputPowerHiHi OBJECT-TYPE
        SYNTAX INTEGER
        ACCESS read-only
        STATUS mandatory
        DESCRIPTION "RF output power (total rms) high alarm threshold in steps of 0.1 dBm."
    ::= { bfeMeasuringValuesEntry 10 }

-- *****
    bfeInputVoltageLoLo OBJECT-TYPE
        SYNTAX INTEGER
        ACCESS read-only
        STATUS mandatory
        DESCRIPTION "The +24V voltage low alarm threshold in steps of 0.1V."
    ::= { bfeMeasuringValuesEntry 11 }

    bfeInputVoltageLo OBJECT-TYPE
        SYNTAX INTEGER
        ACCESS read-only
        STATUS mandatory
        DESCRIPTION "The +24V voltage low warning threshold in steps of 0.1V."
    ::= { bfeMeasuringValuesEntry 12 }

    bfeInputVoltageValue OBJECT-TYPE
        SYNTAX INTEGER
        ACCESS read-only
        STATUS mandatory
        DESCRIPTION "The +24V voltage in steps of 0.1V."
    ::= { bfeMeasuringValuesEntry 13 }

    bfeInputVoltageHi OBJECT-TYPE
        SYNTAX INTEGER
        ACCESS read-only
        STATUS mandatory
        DESCRIPTION "The +24V voltage high warning threshold in steps of 0.1V."
    ::= { bfeMeasuringValuesEntry 14 }

    bfeInputVoltageHiHi OBJECT-TYPE
        SYNTAX INTEGER
        ACCESS read-only
        STATUS mandatory
        DESCRIPTION "The +24V voltage high alarm threshold in steps of 0.1V."
    ::= { bfeMeasuringValuesEntry 15 }

-- *****
    bfeInternalVoltage1LoLo OBJECT-TYPE
        SYNTAX INTEGER
        ACCESS read-only
        STATUS mandatory
        DESCRIPTION "The internal voltage no. 1 low alarm threshold in steps of 0.1V."
    ::= { bfeMeasuringValuesEntry 16 }

    bfeInternalVoltage1Lo OBJECT-TYPE
        SYNTAX INTEGER
        ACCESS read-only
        STATUS mandatory
        DESCRIPTION "The internal voltage no. 1 low warning threshold in steps of 0.1V."
    ::= { bfeMeasuringValuesEntry 17 }

    bfeInternalVoltage1Value OBJECT-TYPE
        SYNTAX INTEGER
        ACCESS read-only
        STATUS mandatory
        DESCRIPTION "The internal voltage no. 1 in steps of 0.1V.
                     see bfeDisplayInternalVoltage1Nominal and bfeDisplayInternalVoltage1Supported"
    ::= { bfeMeasuringValuesEntry 18 }

    bfeInternalVoltage1Hi OBJECT-TYPE
        SYNTAX INTEGER
        ACCESS read-only
        STATUS mandatory
        DESCRIPTION "The internal voltage no. 1 high warning threshold in steps of 0.1V."
    ::= { bfeMeasuringValuesEntry 19 }

    bfeInternalVoltage1HiHi OBJECT-TYPE
        SYNTAX INTEGER
        ACCESS read-only
        STATUS mandatory
        DESCRIPTION "The internal voltage no. 1 high alarm threshold in steps of 0.1V."
    ::= { bfeMeasuringValuesEntry 20 }

-- *****
    bfeInternalVoltage2LoLo OBJECT-TYPE
        SYNTAX INTEGER
        ACCESS read-only
        STATUS mandatory
        DESCRIPTION "The internal voltage no. 2 low alarm threshold in steps of 0.1V."
    ::= { bfeMeasuringValuesEntry 21 }

    bfeInternalVoltage2Lo OBJECT-TYPE
        SYNTAX INTEGER
        ACCESS read-only
        STATUS mandatory
        DESCRIPTION "The internal voltage no. 2 low warning threshold in steps of 0.1V."
    ::= { bfeMeasuringValuesEntry 22 }

    bfeInternalVoltage2Value OBJECT-TYPE
        SYNTAX INTEGER
        ACCESS read-only
        STATUS mandatory
        DESCRIPTION "The internal voltage no. 2 in steps of 0.1V.
                     see bfeDisplayInternalVoltage2Nominal and bfeDisplayInternalVoltage2Supported"
    ::= { bfeMeasuringValuesEntry 23 }

    bfeInternalVoltage2Hi OBJECT-TYPE
        SYNTAX INTEGER
        ACCESS read-only
        STATUS mandatory
        DESCRIPTION "The internal voltage no. 2 high warning threshold in steps of 0.1V."
    ::= { bfeMeasuringValuesEntry 24 }

    bfeInternalVoltage2HiHi OBJECT-TYPE
        SYNTAX INTEGER
        ACCESS read-only
        STATUS mandatory
        DESCRIPTION "The internal voltage no. 2 high alarm threshold in steps of 0.1V."
    ::= { bfeMeasuringValuesEntry 25 }

-- *****
    bfeInternalVoltage3LoLo OBJECT-TYPE
        SYNTAX INTEGER
        ACCESS read-only
        STATUS mandatory
        DESCRIPTION "The internal voltage no. 3 low alarm threshold in steps of 0.1V."
    ::= { bfeMeasuringValuesEntry 26 }

    bfeInternalVoltage3Lo OBJECT-TYPE
        SYNTAX INTEGER
        ACCESS read-only
        STATUS mandatory
        DESCRIPTION "The internal voltage no. 3 low warning threshold in steps of 0.1V."
    ::= { bfeMeasuringValuesEntry 27 }

    bfeInternalVoltage3Value OBJECT-TYPE
        SYNTAX INTEGER
        ACCESS read-only
        STATUS mandatory
        DESCRIPTION "The internal voltage no. 3 in steps of 0.1V.
                     see bfeDisplayInternalVoltage3Nominal and bfeDisplayInternalVoltage3Supported"
    ::= { bfeMeasuringValuesEntry 28 }

    bfeInternalVoltage3Hi OBJECT-TYPE
        SYNTAX INTEGER
        ACCESS read-only
        STATUS mandatory
        DESCRIPTION "The internal voltage no. 3 high warning threshold in steps of 0.1V."
    ::= { bfeMeasuringValuesEntry 29 }

    bfeInternalVoltage3HiHi OBJECT-TYPE
        SYNTAX INTEGER
        ACCESS read-only
        STATUS mandatory
        DESCRIPTION "The internal voltage no. 3 high alarm threshold in steps of 0.1V."
    ::= { bfeMeasuringValuesEntry 30 }

-- #####+5 Space reserved for 1 additional internal voltage measuring value with limits


--*****************************************************************************************
--  bfeStates group

-- Note: For every control OId there must be a correspondant alarm OId!

    bfeStatesTable OBJECT-TYPE
        SYNTAX SEQUENCE OF BfeStatesEntry
        ACCESS not-accessible
        STATUS mandatory
        DESCRIPTION ""
    ::= { bfeStates 1 }

-- table of states entry(ro/rw)

    bfeStatesEntry OBJECT-TYPE
        SYNTAX BfeStatesEntry
        ACCESS not-accessible
        STATUS mandatory
        DESCRIPTION "Alarms for a module."
        INDEX { bfeNESlot }
    ::= { bfeStatesTable 1 }

-- the structure of the entry

    BfeStatesEntry ::= SEQUENCE
    {
        bfeStatesBootloader             PerceivedSeverityValue,
        bfeStatesCommLoss               PerceivedSeverityValue,
        bfeStatesTemperatureLow         PerceivedSeverityValue,
        bfeStatesTemperatureHigh        PerceivedSeverityValue,
        bfeStatesRfOutputPowerLow       PerceivedSeverityValue,
        bfeStatesRfOutputPowerHigh      PerceivedSeverityValue,
        bfeStatesInputVoltageLow        PerceivedSeverityValue,
        bfeStatesInputVoltageHigh       PerceivedSeverityValue,
        bfeStatesInternalVoltage        PerceivedSeverityValue,
        bfeStatesStandby                PerceivedSeverityValue,
        bfeStatesRedundancySwitch       PerceivedSeverityValue,
        -- ** Only for 19 inch devices with supply and fan units
        bfeStatesPowerSupplyLeft        PerceivedSeverityValue,
        bfeStatesPowerSupplyRight       PerceivedSeverityValue,
        bfeStatesFanLeft                PerceivedSeverityValue,
        bfeStatesFanRight               PerceivedSeverityValue
    }

    bfeStatesBootloader OBJECT-TYPE
        SYNTAX PerceivedSeverityValue
        ACCESS read-only
        STATUS mandatory
        DESCRIPTION
            "The device is running in bootloader mode
             without a legal application software."
    ::= { bfeStatesEntry 1 }

    bfeStatesCommLoss OBJECT-TYPE
        SYNTAX PerceivedSeverityValue
        ACCESS read-only
        STATUS mandatory
        DESCRIPTION
            "The NEC has lost the connection to the device.
             Reason may be a removed or defective device.
             Note that this state is set by the NEC and not
             by the device"
    ::= { bfeStatesEntry 2 }

    bfeStatesTemperatureLow OBJECT-TYPE
        SYNTAX PerceivedSeverityValue
        ACCESS read-only
        STATUS mandatory
        DESCRIPTION "Device temperature low"
    ::= { bfeStatesEntry 3 }

    bfeStatesTemperatureHigh OBJECT-TYPE
        SYNTAX PerceivedSeverityValue
        ACCESS read-only
        STATUS mandatory
        DESCRIPTION "Device temperature high"
    ::= { bfeStatesEntry 4 }

    bfeStatesRfOutputPowerLow OBJECT-TYPE
        SYNTAX PerceivedSeverityValue
        ACCESS read-only
        STATUS mandatory
        DESCRIPTION "RF output power (total rms) low"
    ::= { bfeStatesEntry 5 }

    bfeStatesRfOutputPowerHigh OBJECT-TYPE
        SYNTAX PerceivedSeverityValue
        ACCESS read-only
        STATUS mandatory
        DESCRIPTION "RF output power (total rms) high"
    ::= { bfeStatesEntry 6 }

    bfeStatesInputVoltageLow OBJECT-TYPE
        SYNTAX PerceivedSeverityValue
        ACCESS read-only
        STATUS mandatory
        DESCRIPTION "Input voltage low"
    ::= { bfeStatesEntry 7 }

    bfeStatesInputVoltageHigh OBJECT-TYPE
        SYNTAX PerceivedSeverityValue
        ACCESS read-only
        STATUS mandatory
        DESCRIPTION "Input voltage high"
    ::= { bfeStatesEntry 8 }

    bfeStatesInternalVoltage OBJECT-TYPE
        SYNTAX PerceivedSeverityValue
        ACCESS read-only
        STATUS mandatory
        DESCRIPTION "Internal voltage out of range"
    ::= { bfeStatesEntry 9 }

    bfeStatesStandby OBJECT-TYPE
        SYNTAX PerceivedSeverityValue
        ACCESS read-only
        STATUS mandatory
        DESCRIPTION "Device is sleeping, no rf output"
    ::= { bfeStatesEntry 10 }

    bfeStatesRedundancySwitch OBJECT-TYPE
        SYNTAX PerceivedSeverityValue
        ACCESS read-only
        STATUS mandatory
        DESCRIPTION "This (redundant) device has been activated (redundancy switchover)"
    ::= { bfeStatesEntry 11 }

    bfeStatesPowerSupplyLeft OBJECT-TYPE
        SYNTAX PerceivedSeverityValue
        ACCESS read-only
        STATUS mandatory
        DESCRIPTION "The left (looking from front) power supply unit fails.
                     Only valid for devices in 19 inch housing"
    ::= { bfeStatesEntry 12 }

    bfeStatesPowerSupplyRight OBJECT-TYPE
        SYNTAX PerceivedSeverityValue
        ACCESS read-only
        STATUS mandatory
        DESCRIPTION "The right (looking from front) power supply unit fails.
                     Only valid for devices in 19 inch housing"
    ::= { bfeStatesEntry 13 }

    bfeStatesFanLeft OBJECT-TYPE
        SYNTAX PerceivedSeverityValue
        ACCESS read-only
        STATUS mandatory
        DESCRIPTION "The left (looking from front) fan unit fails.
                     Only valid for devices in 19 inch housing"
    ::= { bfeStatesEntry 14 }

    bfeStatesFanRight OBJECT-TYPE
        SYNTAX PerceivedSeverityValue
        ACCESS read-only
        STATUS mandatory
        DESCRIPTION "The right (looking from front) fan unit fails.
                     Only valid for devices in 19 inch housing"
    ::= { bfeStatesEntry 15 }

--*****************************************************************************************
--  bfeControl group

  bfeControlTable OBJECT-TYPE
    SYNTAX SEQUENCE OF BfeControlEntry
    ACCESS not-accessible
    STATUS mandatory
    DESCRIPTION ""
  ::= { bfeControl 1 }

-- table of control entry(ro/rw)

  bfeControlEntry OBJECT-TYPE
    SYNTAX BfeControlEntry
    ACCESS not-accessible
    STATUS mandatory
    DESCRIPTION "Alarms for a module."
    INDEX { bfeNESlot }
  ::= { bfeControlTable 1 }

-- the structure of the entry

    BfeControlEntry ::= SEQUENCE
    {
        bfeControlReset             TruthValue,
        bfeControlModuleLedBlink    TruthValue
    }

    bfeControlReset OBJECT-TYPE
      SYNTAX TruthValue
      ACCESS read-write
      STATUS mandatory
      DESCRIPTION "Reset the module."
    ::= { bfeControlEntry 1 }

    bfeControlModuleLedBlink OBJECT-TYPE
        SYNTAX TruthValue
        ACCESS read-write
        STATUS mandatory
        DESCRIPTION   "Writing this variable to true(1) lets the device's
        modul LED blink green for 10 seconds.
        Writing this variable to false(2) stbfe blinking at once.
        This variable always returns false(2) on read requests"
    ::= { bfeControlEntry 2 }


--*****************************************************************************************
-- bfeConfiguration group

    bfeConfigurationTable OBJECT-TYPE
        SYNTAX SEQUENCE OF BfeConfigurationEntry
        ACCESS not-accessible
        STATUS mandatory
        DESCRIPTION ""
    ::= { bfeConfiguration 1 }

-- table of configuration entry(ro/rw)

    bfeConfigurationEntry OBJECT-TYPE
        SYNTAX BfeConfigurationEntry
        ACCESS not-accessible
        STATUS mandatory
        DESCRIPTION ""
        INDEX { bfeNESlot  }
    ::= { bfeConfigurationTable 1 }

-- the structure of the entry

    BfeConfigurationEntry ::= SEQUENCE
    {
        bfeConfigNESlotWrite         NESlotWriteValue,
        bfeConfigRfMode              RfMode,
        bfeConfigRfGain              INTEGER,
        bfeConfigRedundancyMode      RedundancyMode,
        bfeConfigEqualizer1Level     INTEGER,
        bfeConfigEqualizer2Level     INTEGER,
        bfeConfigEqualizer3Level     INTEGER,
        bfeConfigEqualizer4Level     INTEGER,
        bfeConfigEqualizer5Level     INTEGER,
        bfeConfigEqualizer6Level     INTEGER,
        bfeConfigEqualizer7Level     INTEGER,
        bfeConfigEqualizer8Level     INTEGER
    }

    bfeConfigNESlotWrite OBJECT-TYPE
        SYNTAX NESlotWriteValue
        ACCESS read-write
        STATUS optional
        DESCRIPTION "By writing this variable a slot can be assigned
            for devices that dont support hardware slot detection.
            Reading '-1' means that the slot position is NOT writable."
    ::= { bfeConfigurationEntry 1 }

    bfeConfigRfMode OBJECT-TYPE
        SYNTAX RfMode
        ACCESS read-write
        STATUS mandatory
        DESCRIPTION "The RF mode."
    ::= { bfeConfigurationEntry 2 }

    bfeConfigRfGain OBJECT-TYPE
        SYNTAX INTEGER
        ACCESS read-write
        STATUS mandatory
        DESCRIPTION "The desired offset from nominal gain in 0.1 dB units."
    ::= { bfeConfigurationEntry 3 }

    bfeConfigRedundancyMode OBJECT-TYPE
        SYNTAX RedundancyMode
        ACCESS read-write
        STATUS mandatory
        DESCRIPTION "The redundancy mode."
    ::= { bfeConfigurationEntry 4 }

    bfeConfigEqualizer1Level OBJECT-TYPE
        SYNTAX INTEGER
        ACCESS read-write
        STATUS mandatory
        DESCRIPTION "Level of equalizer no.1"
    ::= { bfeConfigurationEntry 5 }

    bfeConfigEqualizer2Level OBJECT-TYPE
        SYNTAX INTEGER
        ACCESS read-write
        STATUS mandatory
        DESCRIPTION "Level of equalizer no.2"
    ::= { bfeConfigurationEntry 6 }

    bfeConfigEqualizer3Level OBJECT-TYPE
        SYNTAX INTEGER
        ACCESS read-write
        STATUS mandatory
        DESCRIPTION "Level of equalizer no.3"
    ::= { bfeConfigurationEntry 7 }

    bfeConfigEqualizer4Level OBJECT-TYPE
        SYNTAX INTEGER
        ACCESS read-write
        STATUS mandatory
        DESCRIPTION "Level of equalizer no.4"
    ::= { bfeConfigurationEntry 8 }

    bfeConfigEqualizer5Level OBJECT-TYPE
        SYNTAX INTEGER
        ACCESS read-write
        STATUS mandatory
        DESCRIPTION "Level of equalizer no.5"
    ::= { bfeConfigurationEntry 9 }

    bfeConfigEqualizer6Level OBJECT-TYPE
        SYNTAX INTEGER
        ACCESS read-write
        STATUS mandatory
        DESCRIPTION "Level of equalizer no.6"
    ::= { bfeConfigurationEntry 10 }

    bfeConfigEqualizer7Level OBJECT-TYPE
        SYNTAX INTEGER
        ACCESS read-write
        STATUS mandatory
        DESCRIPTION "Level of equalizer no.7"
    ::= { bfeConfigurationEntry 11 }

    bfeConfigEqualizer8Level OBJECT-TYPE
        SYNTAX INTEGER
        ACCESS read-write
        STATUS mandatory
        DESCRIPTION "Level of equalizer no.8"
    ::= { bfeConfigurationEntry 12 }

-- #####+8 Space reserved for 8 additional filters


--*****************************************************************************************
-- Display group

    bfeDisplayTable OBJECT-TYPE
        SYNTAX SEQUENCE OF BfeDisplayEntry
        ACCESS not-accessible
        STATUS mandatory
        DESCRIPTION ""
    ::= { bfeDisplay 1 }

-- table of configuration entry(ro/rw)

    bfeDisplayEntry OBJECT-TYPE
        SYNTAX BfeDisplayEntry
        ACCESS not-accessible
        STATUS mandatory
        DESCRIPTION ""
        INDEX { bfeNESlot  }
    ::= { bfeDisplayTable 1 }

-- the structure of the entry

    BfeDisplayEntry ::= SEQUENCE
    {
        bfeDisplayRedundancySupported         TruthValue,
        bfeDisplayDeviceRedundancyState       DeviceRedundancyState,
        bfeDisplayDeviceActivity              DeviceActivityState,

        bfeDisplayEqualizer1Frequency         INTEGER,
        bfeDisplayEqualizer2Frequency         INTEGER,
        bfeDisplayEqualizer3Frequency         INTEGER,
        bfeDisplayEqualizer4Frequency         INTEGER,
        bfeDisplayEqualizer5Frequency         INTEGER,
        bfeDisplayEqualizer6Frequency         INTEGER,
        bfeDisplayEqualizer7Frequency         INTEGER,
        bfeDisplayEqualizer8Frequency         INTEGER,

        bfeDisplayInternalVoltage1Supported   TruthValue,
        bfeDisplayInternalVoltage2Supported   TruthValue,
        bfeDisplayInternalVoltage3Supported   TruthValue,
                                                
        bfeDisplayInputVoltageNominal         INTEGER,
        bfeDisplayInternalVoltage1Nominal     INTEGER,
        bfeDisplayInternalVoltage2Nominal     INTEGER,
        bfeDisplayInternalVoltage3Nominal     INTEGER
    }

    bfeDisplayRedundancySupported OBJECT-TYPE
        SYNTAX  TruthValue
        ACCESS  read-only
        STATUS  mandatory
        DESCRIPTION "Returns true(1) if a the device supports redundancy"
    ::={ bfeDisplayEntry 1 }

    bfeDisplayDeviceRedundancyState OBJECT-TYPE
        SYNTAX  DeviceRedundancyState
        ACCESS  read-only
        STATUS  mandatory
        DESCRIPTION "Returns the device's redundancy state"
    ::={ bfeDisplayEntry 2 }

    bfeDisplayDeviceActivity OBJECT-TYPE
        SYNTAX  DeviceActivityState
        ACCESS  read-only
        STATUS  mandatory
        DESCRIPTION "Returns the actual device's activity state"
    ::={ bfeDisplayEntry 3 }

    bfeDisplayEqualizer1Frequency OBJECT-TYPE
        SYNTAX INTEGER
        ACCESS read-only
        STATUS mandatory
        DESCRIPTION "Frequency of equalizer no.1"
    ::= { bfeDisplayEntry 4 }

    bfeDisplayEqualizer2Frequency OBJECT-TYPE
        SYNTAX INTEGER
        ACCESS read-only
        STATUS mandatory
        DESCRIPTION "Frequency of equalizer no.2"
    ::= { bfeDisplayEntry 5 }

    bfeDisplayEqualizer3Frequency OBJECT-TYPE
        SYNTAX INTEGER
        ACCESS read-only
        STATUS mandatory
        DESCRIPTION "Frequency of equalizer no.3"
    ::= { bfeDisplayEntry 6 }

    bfeDisplayEqualizer4Frequency OBJECT-TYPE
        SYNTAX INTEGER
        ACCESS read-only
        STATUS mandatory
        DESCRIPTION "Frequency of equalizer no.4"
    ::= { bfeDisplayEntry 7 }

    bfeDisplayEqualizer5Frequency OBJECT-TYPE
        SYNTAX INTEGER
        ACCESS read-only
        STATUS mandatory
        DESCRIPTION "Frequency of equalizer no.5"
    ::= { bfeDisplayEntry 8 }

    bfeDisplayEqualizer6Frequency OBJECT-TYPE
        SYNTAX INTEGER
        ACCESS read-only
        STATUS mandatory
        DESCRIPTION "Frequency of equalizer no.6"
    ::= { bfeDisplayEntry 9 }

    bfeDisplayEqualizer7Frequency OBJECT-TYPE
        SYNTAX INTEGER
        ACCESS read-only
        STATUS mandatory
        DESCRIPTION "Frequency of equalizer no.7"
    ::= { bfeDisplayEntry 10 }

    bfeDisplayEqualizer8Frequency OBJECT-TYPE
        SYNTAX INTEGER
        ACCESS read-only
        STATUS mandatory
        DESCRIPTION "Frequency of equalizer no.8"
    ::= { bfeDisplayEntry 11 }

-- #####+8 Space reserved for 8 additional filters

    bfeDisplayInternalVoltage1Supported OBJECT-TYPE
        SYNTAX  TruthValue
        ACCESS  read-only
        STATUS  mandatory
        DESCRIPTION "Reports true(1) if internal voltage no. 1 is supported"
    ::={ bfeDisplayEntry 20 }

    bfeDisplayInternalVoltage2Supported OBJECT-TYPE
        SYNTAX  TruthValue
        ACCESS  read-only
        STATUS  mandatory
        DESCRIPTION "Reports true(1) if internal voltage no. 2 is supported"
    ::={ bfeDisplayEntry 21 }

    bfeDisplayInternalVoltage3Supported OBJECT-TYPE
        SYNTAX  TruthValue
        ACCESS  read-only
        STATUS  mandatory
        DESCRIPTION "Reports true(1) if internal voltage no. 3 is supported"
    ::={ bfeDisplayEntry 22 }

-- #####+1 Space reserved for 1 additional internal voltage

    bfeDisplayInputVoltageNominal OBJECT-TYPE
        SYNTAX  INTEGER
        ACCESS  read-only
        STATUS  mandatory
        DESCRIPTION "The nominal input voltage"
    ::={ bfeDisplayEntry 24 }

    bfeDisplayInternalVoltage1Nominal OBJECT-TYPE
        SYNTAX  INTEGER
        ACCESS  read-only
        STATUS  mandatory
        DESCRIPTION "The nominal internal voltage no. 1"
    ::={ bfeDisplayEntry 25 }

    bfeDisplayInternalVoltage2Nominal OBJECT-TYPE
        SYNTAX  INTEGER
        ACCESS  read-only
        STATUS  mandatory
        DESCRIPTION "The nominal internal voltage no. 2"
    ::={ bfeDisplayEntry 26 }

    bfeDisplayInternalVoltage3Nominal OBJECT-TYPE
        SYNTAX  INTEGER
        ACCESS  read-only
        STATUS  mandatory
        DESCRIPTION "The nominal internal voltage no. 3"
    ::={ bfeDisplayEntry 27 }

-- #####+1 Space reserved for 1 additional internal voltage



--*****************************************************************************************
END
