-- *********************************************************************************************
-- *
-- * Description:   Implements definitions for the Ova-modul
-- *                (Optical Amplifier with design release V11)
-- *
-- * Copyright 2003 by BKtel communications GmbH
-- *
-- *     V.0.1 07.05.03  M. Heldmann    first draft
-- *     V.0.2 23.07.03  M. Heldmann    added descriptions for the states
-- *     V.0.3 22.09.03  M. Heldmann    changed descriptions for ovaDisplayOutputPwrOrGainAdjust...
-- *     V.1.0 17.12.03  M. Heldmann    added ovaDisplayOutputPwrOrGainNominal, ovaStatesRedundancySwitch, 
-- *                                          ovaConfigInputPwrLimitHiHi..ovaConfigMaskExtIO
-- *     V.1.1 27.02.04  M. Heldmann    changed ExtIOmask parameter name from maskUnknown(3) to maskSpecial(3)
-- *     V.1.2 30.09.04  M. Heldmann    modified description of ovaStatesOutputHigh, ovaStatesOutputLow
-- *     V.1.3 27.01.05  M. Heldmann    added ovaStatesReturnLossLow, ovaStatesReturnLossHigh,
-- *                                          ovaControlSbsEvaluationStart, ovaConfigSbsEvaluationMode, 
-- *                                          ovaReturnLossMin ... ovaReturnLossMax,
-- *                                          ovaDisplaySbsEvaluatedThreshold ... ovaDisplaySbsLastEvaluationTime
-- *     V.1.4 04.10.06  M. Heldmann    NESlotWriteValue expanded due to new 2G6 platform needs
-- *     V.1.5 26.03.07  M. Heldmann    corrected some descriptions
-- *     V.1.6 29.05.08  M. Heldmann    renamed threshold parameters in xxxxMeasuringValuesTable
-- *     V.1.6 11.07.13  M. Heldmann    adjusted syntax of "CommonEntry" to remove MIB compiler warnings
-- *     V.1.7 05.09.14  M. Heldmann    changed CommonModuleWidth and ConfigNESlotWrite STATUS to optional
-- *********************************************************************************************

BKTEL-HFC862-OVA-V11-MIB DEFINITIONS ::= BEGIN

    IMPORTS
        experimental, enterprises, TimeTicks, IpAddress, Counter
                 FROM RFC1155-SMI
    OBJECT-TYPE
                 FROM RFC-1212
        TRAP-TYPE
                 FROM RFC-1215
        modules, DisplayString, TruthValue, PerceivedSeverityValue, NESlotValue, ModuleWidthValue
                 FROM   BKTEL-HFC862-BASE-MIB
    ;

    ova                 OBJECT IDENTIFIER ::= { modules 102 }
    ovaCommon           OBJECT IDENTIFIER ::= { ova 1 }
    ovaStates           OBJECT IDENTIFIER ::= { ova 2 }
    ovaConfiguration    OBJECT IDENTIFIER ::= { ova 3 }
    ovaControl          OBJECT IDENTIFIER ::= { ova 4 }
    ovaMeasuringValues  OBJECT IDENTIFIER ::= { ova 5 }
    ovaDisplay          OBJECT IDENTIFIER ::= { ova 6 }


--
-- Type definitions
--


        RegulationMode ::= INTEGER
            {
            regModeConstantOutputPower(1),
            regModeConstantGain(2)
            }

        SbsEvaluationMode ::= INTEGER
            {
            evalModeDefault(1),
            evalModeFullScan(2)
            }

        SbsEvaluationState ::= INTEGER
            {
            evaluationNotSupported(1),
            evaluationDone(2),
            evaluationInProgress(3),
            evaluationFailed(4)
            }

        ExtIOmode ::= INTEGER
            {
            modeActiveLowOutput(1),   
            modeActiveHighOutput(2),  
            modeRedundantMasterIrreversible(3),   
            modeRedundantMasterFallback(4),   
            modeRedundantSlave(5)
            }

        ExtIOmask ::= INTEGER
            {
            maskAlarmsOnly(1),
            maskAlarmsAndWarnings(2),
            maskSpecial(3)           -- This item is NOT writable !!
            }

        NESlotWriteValue ::= INTEGER (-1..99)


--*****************************************************************************************
-- OVA ( Optical Amplifier with design release V11 )

--*****************************************************************************************
-- ovaCommon group

    ovaCommonNumberOfModules OBJECT-TYPE
        SYNTAX  INTEGER(0..50)
        ACCESS  read-only
        STATUS  mandatory
        DESCRIPTION "Number of modules in table."
  ::= { ovaCommon 1 }

    ovaCommonTable OBJECT-TYPE
        SYNTAX SEQUENCE OF OvaCommonEntry
        ACCESS not-accessible
        STATUS mandatory
        DESCRIPTION "The table contains all modules of the OVA-type in the NE"
  ::= { ovaCommon 2 }

-- table of states entry(ro/rw)

    ovaCommonEntry OBJECT-TYPE
        SYNTAX OvaCommonEntry
        ACCESS not-accessible
        STATUS mandatory
        DESCRIPTION "Common-Values for a module."
        INDEX { ovaNESlot }
  ::= { ovaCommonTable 1 }

-- the structure of the entry

    OvaCommonEntry ::= SEQUENCE
    {
        ovaNESlot                      NESlotValue,
        ovaCommonType                  DisplayString,
        ovaCommonDescr                 DisplayString,
        ovaCommonFirmwareId            DisplayString,
        ovaCommonModuleWidth           ModuleWidthValue
    }

    ovaNESlot OBJECT-TYPE
        SYNTAX  NESlotValue
        ACCESS  read-only
        STATUS  mandatory
        DESCRIPTION
        "The slot number of the chassis for which this
        entry contains management information."
    ::= { ovaCommonEntry 1 }

    ovaCommonType OBJECT-TYPE
        SYNTAX  DisplayString  (SIZE(0..32))
        ACCESS  read-only
        STATUS  mandatory
        DESCRIPTION
        "The type of physical module. modSlotEmpty indicates
         an empty slot.  A Value of modSlotUnknown indicates
         that the type of module is unknown."
    ::= { ovaCommonEntry 2 }

    ovaCommonDescr OBJECT-TYPE
        SYNTAX  DisplayString
        ACCESS  read-write
        STATUS  mandatory
        DESCRIPTION
        "A textual description of the module.
        If not available, this Value should be
        set to a zero length string."
    ::= { ovaCommonEntry 3 }

    ovaCommonFirmwareId OBJECT-TYPE
        SYNTAX DisplayString (SIZE(0..32))
        ACCESS read-only
        STATUS mandatory
        DESCRIPTION "The firmware Id of the module."
    ::= { ovaCommonEntry 4 }

    ovaCommonModuleWidth OBJECT-TYPE
        SYNTAX ModuleWidthValue
        ACCESS read-only
        STATUS optional
        DESCRIPTION "The width of the module in multiples of slots (1, 2, ...)"
    ::= { ovaCommonEntry 5 }

--*****************************************************************************************
-- ovaMeasuringValues group

-- table of measuring Values

    ovaMeasuringValuesTable OBJECT-TYPE
        SYNTAX SEQUENCE OF OvaMeasuringValuesEntry
        ACCESS not-accessible
        STATUS mandatory
        DESCRIPTION ""
   ::= { ovaMeasuringValues 1 }

-- table of measuring Values entry

    ovaMeasuringValuesEntry OBJECT-TYPE
        SYNTAX OvaMeasuringValuesEntry
        ACCESS not-accessible
        STATUS mandatory
        DESCRIPTION "Common-Values for a module."
        INDEX { ovaNESlot }
  ::= { ovaMeasuringValuesTable 1 }

--  the structure of the entry

    OvaMeasuringValuesEntry ::= SEQUENCE
    {
        ovaInputPowerLoLo              INTEGER,
        ovaInputPowerLo                INTEGER,
        ovaInputPowerValue             INTEGER,
        ovaInputPowerHi                INTEGER,
        ovaInputPowerHiHi              INTEGER,

        ovaOutputPowerLoLo             INTEGER,
        ovaOutputPowerLo               INTEGER,
        ovaOutputPowerValue            INTEGER,
        ovaOutputPowerHi               INTEGER,
        ovaOutputPowerHiHi             INTEGER,

        ovaGainLoLo                    INTEGER,
        ovaGainLo                      INTEGER,
        ovaGainValue                   INTEGER,
        ovaGainHi                      INTEGER,
        ovaGainHiHi                    INTEGER,

        ovaLaser1CurrentRelLoLo        INTEGER,
        ovaLaser1CurrentRelLo          INTEGER,
        ovaLaser1CurrentRelValue       INTEGER,
        ovaLaser1CurrentRelHi          INTEGER,
        ovaLaser1CurrentRelHiHi        INTEGER,

        ovaLaser1TecRelLoLo            INTEGER,
        ovaLaser1TecRelLo              INTEGER,
        ovaLaser1TecRelValue           INTEGER,
        ovaLaser1TecRelHi              INTEGER,
        ovaLaser1TecRelHiHi            INTEGER,

        ovaLaser1TemperatureLoLo       INTEGER,
        ovaLaser1TemperatureLo         INTEGER,
        ovaLaser1TemperatureValue      INTEGER,
        ovaLaser1TemperatureHi         INTEGER,
        ovaLaser1TemperatureHiHi       INTEGER,

        ovaLaser1Plus3p3VLoLo          INTEGER,
        ovaLaser1Plus3p3VLo            INTEGER,
        ovaLaser1Plus3p3VValue         INTEGER,
        ovaLaser1Plus3p3VHi            INTEGER,
        ovaLaser1Plus3p3VHiHi          INTEGER,

        ovaLaser2CurrentRelLoLo        INTEGER,
        ovaLaser2CurrentRelLo          INTEGER,
        ovaLaser2CurrentRelValue       INTEGER,
        ovaLaser2CurrentRelHi          INTEGER,
        ovaLaser2CurrentRelHiHi        INTEGER,

        ovaLaser2TecRelLoLo            INTEGER,
        ovaLaser2TecRelLo              INTEGER,
        ovaLaser2TecRelValue           INTEGER,
        ovaLaser2TecRelHi              INTEGER,
        ovaLaser2TecRelHiHi            INTEGER,

        ovaLaser2TemperatureLoLo       INTEGER,
        ovaLaser2TemperatureLo         INTEGER,
        ovaLaser2TemperatureValue      INTEGER,
        ovaLaser2TemperatureHi         INTEGER,
        ovaLaser2TemperatureHiHi       INTEGER,

        ovaLaser2Plus3p3VLoLo          INTEGER,
        ovaLaser2Plus3p3VLo            INTEGER,
        ovaLaser2Plus3p3VValue         INTEGER,
        ovaLaser2Plus3p3VHi            INTEGER,
        ovaLaser2Plus3p3VHiHi          INTEGER,

        ovaPlus3p3VLoLo                INTEGER,
        ovaPlus3p3VLo                  INTEGER,
        ovaPlus3p3VValue               INTEGER,
        ovaPlus3p3VHi                  INTEGER,
        ovaPlus3p3VHiHi                INTEGER,

        ovaPlus5VLoLo                  INTEGER,
        ovaPlus5VLo                    INTEGER,
        ovaPlus5VValue                 INTEGER,
        ovaPlus5VHi                    INTEGER,
        ovaPlus5VHiHi                  INTEGER,

        ovaPlus10VLoLo                 INTEGER,
        ovaPlus10VLo                   INTEGER,
        ovaPlus10VValue                INTEGER,
        ovaPlus10VHi                   INTEGER,
        ovaPlus10VHiHi                 INTEGER,

        ovaPlus24VLoLo                 INTEGER,
        ovaPlus24VLo                   INTEGER,
        ovaPlus24VValue                INTEGER,
        ovaPlus24VHi                   INTEGER,
        ovaPlus24VHiHi                 INTEGER,

        ovaTemperatureLoLo             INTEGER,
        ovaTemperatureLo               INTEGER,
        ovaTemperatureValue            INTEGER,
        ovaTemperatureHi               INTEGER,
        ovaTemperatureHiHi             INTEGER,

        ovaReturnLossLoLo              INTEGER,
        ovaReturnLossLo                INTEGER,
        ovaReturnLossValue             INTEGER,
        ovaReturnLossHi                INTEGER,
        ovaReturnLossHiHi              INTEGER
    }

-- *****
    ovaInputPowerLoLo OBJECT-TYPE
        SYNTAX INTEGER
        ACCESS read-only
        STATUS mandatory
        DESCRIPTION "Input power low alarm threshold in steps of 0.1dBm."
    ::= { ovaMeasuringValuesEntry 1 }

    ovaInputPowerLo OBJECT-TYPE
        SYNTAX INTEGER
        ACCESS read-only
        STATUS mandatory
        DESCRIPTION "Input power low warning threshold in steps of 0.1dBm."
    ::= { ovaMeasuringValuesEntry 2 }

    ovaInputPowerValue OBJECT-TYPE
        SYNTAX INTEGER
        ACCESS read-only
        STATUS mandatory
        DESCRIPTION "Input power in steps of 0.1dBm."
    ::= { ovaMeasuringValuesEntry 3 }

    ovaInputPowerHi OBJECT-TYPE
        SYNTAX INTEGER
        ACCESS read-only
        STATUS mandatory
        DESCRIPTION "Input power high warning threshold in steps of 0.1dBm."
    ::= { ovaMeasuringValuesEntry 4 }

    ovaInputPowerHiHi OBJECT-TYPE
        SYNTAX INTEGER
        ACCESS read-only
        STATUS mandatory
        DESCRIPTION "Input power high alarm threshold in steps of 0.1dBm."
    ::= { ovaMeasuringValuesEntry 5 }

-- *****
    ovaOutputPowerLoLo OBJECT-TYPE
        SYNTAX INTEGER
        ACCESS read-only
        STATUS mandatory
        DESCRIPTION "Output power low alarm threshold in steps of 0.1dBm."
    ::= { ovaMeasuringValuesEntry 6 }

    ovaOutputPowerLo OBJECT-TYPE
        SYNTAX INTEGER
        ACCESS read-only
        STATUS mandatory
        DESCRIPTION "Output power low warning threshold in steps of 0.1dBm."
    ::= { ovaMeasuringValuesEntry 7 }

    ovaOutputPowerValue OBJECT-TYPE
        SYNTAX INTEGER
        ACCESS read-only
        STATUS mandatory
        DESCRIPTION "Output power in steps of 0.1dBm."
    ::= { ovaMeasuringValuesEntry 8 }

    ovaOutputPowerHi OBJECT-TYPE
        SYNTAX INTEGER
        ACCESS read-only
        STATUS mandatory
        DESCRIPTION "Output power high warning threshold in steps of 0.1dBm."
    ::= { ovaMeasuringValuesEntry 9 }

    ovaOutputPowerHiHi OBJECT-TYPE
        SYNTAX INTEGER
        ACCESS read-only
        STATUS mandatory
        DESCRIPTION "Output power high alarm threshold in steps of 0.1dBm."
    ::= { ovaMeasuringValuesEntry 10 }

-- *****
    ovaGainLoLo OBJECT-TYPE
        SYNTAX INTEGER
        ACCESS read-only
        STATUS mandatory
        DESCRIPTION "Gain low alarm threshold in steps of 0.1dB."
    ::= { ovaMeasuringValuesEntry 11 }

    ovaGainLo OBJECT-TYPE
        SYNTAX INTEGER
        ACCESS read-only
        STATUS mandatory
        DESCRIPTION "Gain low warning threshold in steps of 0.1dB."
    ::= { ovaMeasuringValuesEntry 12 }

    ovaGainValue OBJECT-TYPE
        SYNTAX INTEGER
        ACCESS read-only
        STATUS mandatory
        DESCRIPTION "Gain in steps of 0.1dB."
    ::= { ovaMeasuringValuesEntry 13 }

    ovaGainHi OBJECT-TYPE
        SYNTAX INTEGER
        ACCESS read-only
        STATUS mandatory
        DESCRIPTION "Gain high warning threshold in steps of 0.1dB."
    ::= { ovaMeasuringValuesEntry 14 }

    ovaGainHiHi OBJECT-TYPE
        SYNTAX INTEGER
        ACCESS read-only
        STATUS mandatory
        DESCRIPTION "Gain high alarm threshold in steps of 0.1dB."
    ::= { ovaMeasuringValuesEntry 15 }

-- *****
    ovaLaser1CurrentRelLoLo OBJECT-TYPE
        SYNTAX INTEGER
        ACCESS read-only
        STATUS mandatory
        DESCRIPTION "Relative laser no.1 current low alarm threshold in steps of 0.1%."
    ::= { ovaMeasuringValuesEntry 16 }

    ovaLaser1CurrentRelLo OBJECT-TYPE
        SYNTAX INTEGER
        ACCESS read-only
        STATUS mandatory
        DESCRIPTION "Relative laser no.1 current low warning threshold in steps of 0.1%."
    ::= { ovaMeasuringValuesEntry 17 }

    ovaLaser1CurrentRelValue OBJECT-TYPE
        SYNTAX INTEGER
        ACCESS read-only
        STATUS mandatory
        DESCRIPTION "The laser no.1 current relative to the current at
                         begin of life in steps of 0.1%."
    ::= { ovaMeasuringValuesEntry 18 }

    ovaLaser1CurrentRelHi OBJECT-TYPE
        SYNTAX INTEGER
        ACCESS read-only
        STATUS mandatory
        DESCRIPTION "Relative laser no.1 current high warning threshold in steps of 0.1%."
    ::= { ovaMeasuringValuesEntry 19 }

    ovaLaser1CurrentRelHiHi OBJECT-TYPE
        SYNTAX INTEGER
        ACCESS read-only
        STATUS mandatory
        DESCRIPTION "Relative laser no.1 current high alarm threshold in steps of 0.1%."
    ::= { ovaMeasuringValuesEntry 20 }

-- *****
    ovaLaser1TecRelLoLo OBJECT-TYPE
        SYNTAX INTEGER
        ACCESS read-only
        STATUS mandatory
        DESCRIPTION "Thermo-electric-cooler current of laser no.1 low alarm threshold in steps of 0.1%."
    ::= { ovaMeasuringValuesEntry 21 }

    ovaLaser1TecRelLo OBJECT-TYPE
        SYNTAX INTEGER
        ACCESS read-only
        STATUS mandatory
        DESCRIPTION "Thermo-electric-cooler current of laser no.1 low warning threshold in steps of 0.1%."
    ::= { ovaMeasuringValuesEntry 22 }

    ovaLaser1TecRelValue OBJECT-TYPE
        SYNTAX INTEGER
        ACCESS read-only
        STATUS mandatory
        DESCRIPTION "The thermo-electric-cooler current of laser no.1 relative to
                         its absolute high alarm threshold in steps of 0.1%."
    ::= { ovaMeasuringValuesEntry 23 }

    ovaLaser1TecRelHi OBJECT-TYPE
        SYNTAX INTEGER
        ACCESS read-only
        STATUS mandatory
        DESCRIPTION "Thermo-electric-cooler current of laser no.1 high warning threshold in steps of 0.1%."
    ::= { ovaMeasuringValuesEntry 24 }

    ovaLaser1TecRelHiHi OBJECT-TYPE
        SYNTAX INTEGER
        ACCESS read-only
        STATUS mandatory
        DESCRIPTION "Thermo-electric-cooler current of laser no.1 high alarm threshold in steps of 0.1%."
    ::= { ovaMeasuringValuesEntry 25 }

-- *****
    ovaLaser1TemperatureLoLo OBJECT-TYPE
        SYNTAX INTEGER
        ACCESS read-only
        STATUS mandatory
        DESCRIPTION "Temperature of laser no.1 low alarm threshold in steps of 0.1 Celsius Degrees."
    ::= { ovaMeasuringValuesEntry 26 }

    ovaLaser1TemperatureLo OBJECT-TYPE
        SYNTAX INTEGER
        ACCESS read-only
        STATUS mandatory
        DESCRIPTION "Temperature of laser no.1 low warning threshold in steps of 0.1 Celsius Degrees."
    ::= { ovaMeasuringValuesEntry 27 }

    ovaLaser1TemperatureValue OBJECT-TYPE
        SYNTAX INTEGER
        ACCESS read-only
        STATUS mandatory
        DESCRIPTION "Temperature of laser no.1 in steps of 0.1 Celsius Degrees."
    ::= { ovaMeasuringValuesEntry 28 }

    ovaLaser1TemperatureHi OBJECT-TYPE
        SYNTAX INTEGER
        ACCESS read-only
        STATUS mandatory
        DESCRIPTION "Temperature of laser no.1 high warning threshold in steps of 0.1 Celsius Degrees."
    ::= { ovaMeasuringValuesEntry 29 }

    ovaLaser1TemperatureHiHi OBJECT-TYPE
        SYNTAX INTEGER
        ACCESS read-only
        STATUS mandatory
        DESCRIPTION "Temperature of laser no.1 high alarm threshold in steps of 0.1 Celsius Degrees."
    ::= { ovaMeasuringValuesEntry 30 }

-- *****
    ovaLaser1Plus3p3VLoLo OBJECT-TYPE
        SYNTAX INTEGER
        ACCESS read-only
        STATUS mandatory
        DESCRIPTION "The 3.3V supply voltage of laser no.1 low alarm threshold in steps of 0.1 Volts."
    ::= { ovaMeasuringValuesEntry 31 }

    ovaLaser1Plus3p3VLo OBJECT-TYPE
        SYNTAX INTEGER
        ACCESS read-only
        STATUS mandatory
        DESCRIPTION "The 3.3V supply voltage of laser no.1 low warning threshold in steps of 0.1 Volts."
    ::= { ovaMeasuringValuesEntry 32 }

    ovaLaser1Plus3p3VValue OBJECT-TYPE
        SYNTAX INTEGER
        ACCESS read-only
        STATUS mandatory
        DESCRIPTION "The 3.3V supply voltage of laser no.1 in steps of 0.1 Volts."
    ::= { ovaMeasuringValuesEntry 33 }

    ovaLaser1Plus3p3VHi OBJECT-TYPE
        SYNTAX INTEGER
        ACCESS read-only
        STATUS mandatory
        DESCRIPTION "The 3.3V supply voltage of laser no.1 high warning threshold in steps of 0.1 Volts."
    ::= { ovaMeasuringValuesEntry 34 }

    ovaLaser1Plus3p3VHiHi OBJECT-TYPE
        SYNTAX INTEGER
        ACCESS read-only
        STATUS mandatory
        DESCRIPTION "The 3.3V supply voltage of laser no.1 high alarm threshold in steps of 0.1 Volts."
    ::= { ovaMeasuringValuesEntry 35 }

-- *****
    ovaLaser2CurrentRelLoLo OBJECT-TYPE
        SYNTAX INTEGER
        ACCESS read-only
        STATUS mandatory
        DESCRIPTION "Relative laser no.2 current low alarm threshold in steps of 0.1%."
    ::= { ovaMeasuringValuesEntry 36 }

    ovaLaser2CurrentRelLo OBJECT-TYPE
        SYNTAX INTEGER
        ACCESS read-only
        STATUS mandatory
        DESCRIPTION "Relative laser no.2 current low warning threshold in steps of 0.1%."
    ::= { ovaMeasuringValuesEntry 37 }

    ovaLaser2CurrentRelValue OBJECT-TYPE
        SYNTAX INTEGER
        ACCESS read-only
        STATUS mandatory
        DESCRIPTION "The laser no.2 current relative to the current at
                         begin of life in steps of 0.1%."
    ::= { ovaMeasuringValuesEntry 38 }

    ovaLaser2CurrentRelHi OBJECT-TYPE
        SYNTAX INTEGER
        ACCESS read-only
        STATUS mandatory
        DESCRIPTION "Relative laser no.2 current high warning threshold in steps of 0.1%."
    ::= { ovaMeasuringValuesEntry 39 }

    ovaLaser2CurrentRelHiHi OBJECT-TYPE
        SYNTAX INTEGER
        ACCESS read-only
        STATUS mandatory
        DESCRIPTION "Relative laser no.2 current high alarm threshold in steps of 0.1%."
    ::= { ovaMeasuringValuesEntry 40 }

-- *****
    ovaLaser2TecRelLoLo OBJECT-TYPE
        SYNTAX INTEGER
        ACCESS read-only
        STATUS mandatory
        DESCRIPTION "Thermo-electric-cooler current of laser no.2 low alarm threshold in steps of 0.1%."
    ::= { ovaMeasuringValuesEntry 41 }

    ovaLaser2TecRelLo OBJECT-TYPE
        SYNTAX INTEGER
        ACCESS read-only
        STATUS mandatory
        DESCRIPTION "Thermo-electric-cooler current of laser no.2 low warning threshold in steps of 0.1%."
    ::= { ovaMeasuringValuesEntry 42 }

    ovaLaser2TecRelValue OBJECT-TYPE
        SYNTAX INTEGER
        ACCESS read-only
        STATUS mandatory
        DESCRIPTION "The thermo-electric-cooler current of laser no.2 relative to
                         its absolute high alarm threshold in steps of 0.1%."
    ::= { ovaMeasuringValuesEntry 43 }

    ovaLaser2TecRelHi OBJECT-TYPE
        SYNTAX INTEGER
        ACCESS read-only
        STATUS mandatory
        DESCRIPTION "Thermo-electric-cooler current of laser no.2 high warning threshold in steps of 0.1%."
    ::= { ovaMeasuringValuesEntry 44 }

    ovaLaser2TecRelHiHi OBJECT-TYPE
        SYNTAX INTEGER
        ACCESS read-only
        STATUS mandatory
        DESCRIPTION "Thermo-electric-cooler current of laser no.2 high alarm threshold in steps of 0.1%."
    ::= { ovaMeasuringValuesEntry 45 }

-- *****
    ovaLaser2TemperatureLoLo OBJECT-TYPE
        SYNTAX INTEGER
        ACCESS read-only
        STATUS mandatory
        DESCRIPTION "Temperature of laser no.2 low alarm threshold in steps of 0.1 Celsius Degrees."
    ::= { ovaMeasuringValuesEntry 46 }

    ovaLaser2TemperatureLo OBJECT-TYPE
        SYNTAX INTEGER
        ACCESS read-only
        STATUS mandatory
        DESCRIPTION "Temperature of laser no.2 low warning threshold in steps of 0.1 Celsius Degrees."
    ::= { ovaMeasuringValuesEntry 47 }

    ovaLaser2TemperatureValue OBJECT-TYPE
        SYNTAX INTEGER
        ACCESS read-only
        STATUS mandatory
        DESCRIPTION "Temperature of laser no.2 in steps of 0.1 Celsius Degrees."
    ::= { ovaMeasuringValuesEntry 48 }

    ovaLaser2TemperatureHi OBJECT-TYPE
        SYNTAX INTEGER
        ACCESS read-only
        STATUS mandatory
        DESCRIPTION "Temperature of laser no.2 high warning threshold in steps of 0.1 Celsius Degrees."
    ::= { ovaMeasuringValuesEntry 49 }

    ovaLaser2TemperatureHiHi OBJECT-TYPE
        SYNTAX INTEGER
        ACCESS read-only
        STATUS mandatory
        DESCRIPTION "Temperature of laser no.2 high alarm threshold in steps of 0.1 Celsius Degrees."
    ::= { ovaMeasuringValuesEntry 50 }

-- *****
    ovaLaser2Plus3p3VLoLo OBJECT-TYPE
        SYNTAX INTEGER
        ACCESS read-only
        STATUS mandatory
        DESCRIPTION "The 3.3V supply voltage of laser no.2 low alarm threshold in steps of 0.1 Volts."
    ::= { ovaMeasuringValuesEntry 51 }

    ovaLaser2Plus3p3VLo OBJECT-TYPE
        SYNTAX INTEGER
        ACCESS read-only
        STATUS mandatory
        DESCRIPTION "The 3.3V supply voltage of laser no.2 low warning threshold in steps of 0.1 Volts."
    ::= { ovaMeasuringValuesEntry 52 }

    ovaLaser2Plus3p3VValue OBJECT-TYPE
        SYNTAX INTEGER
        ACCESS read-only
        STATUS mandatory
        DESCRIPTION "The 3.3V supply voltage of laser no.2 in steps of 0.1 Volts."
    ::= { ovaMeasuringValuesEntry 53 }

    ovaLaser2Plus3p3VHi OBJECT-TYPE
        SYNTAX INTEGER
        ACCESS read-only
        STATUS mandatory
        DESCRIPTION "The 3.3V supply voltage of laser no.2 high warning threshold in steps of 0.1 Volts."
    ::= { ovaMeasuringValuesEntry 54 }

    ovaLaser2Plus3p3VHiHi OBJECT-TYPE
        SYNTAX INTEGER
        ACCESS read-only
        STATUS mandatory
        DESCRIPTION "The 3.3V supply voltage of laser no.2 high alarm threshold in steps of 0.1 Volts."
    ::= { ovaMeasuringValuesEntry 55 }

-- *****
    ovaPlus3p3VLoLo OBJECT-TYPE
        SYNTAX INTEGER
        ACCESS read-only
        STATUS mandatory
        DESCRIPTION "The 3.3V supply voltage low alarm threshold in steps of 0.1 Volts."
    ::= { ovaMeasuringValuesEntry 56 }

    ovaPlus3p3VLo OBJECT-TYPE
        SYNTAX INTEGER
        ACCESS read-only
        STATUS mandatory
        DESCRIPTION "The 3.3V supply voltage low warning threshold in steps of 0.1 Volts."
    ::= { ovaMeasuringValuesEntry 57 }

    ovaPlus3p3VValue OBJECT-TYPE
        SYNTAX INTEGER
        ACCESS read-only
        STATUS mandatory
        DESCRIPTION "The 3.3V supply voltage in steps of 0.1 Volts."
    ::= { ovaMeasuringValuesEntry 58 }

    ovaPlus3p3VHi OBJECT-TYPE
        SYNTAX INTEGER
        ACCESS read-only
        STATUS mandatory
        DESCRIPTION "The 3.3V supply voltage high warning threshold in steps of 0.1 Volts."
    ::= { ovaMeasuringValuesEntry 59 }

    ovaPlus3p3VHiHi OBJECT-TYPE
        SYNTAX INTEGER
        ACCESS read-only
        STATUS mandatory
        DESCRIPTION "The 3.3V supply voltage high alarm threshold in steps of 0.1 Volts."
    ::= { ovaMeasuringValuesEntry 60 }

-- *****
    ovaPlus5VLoLo OBJECT-TYPE
        SYNTAX INTEGER
        ACCESS read-only
        STATUS mandatory
        DESCRIPTION "The 5V supply voltage low alarm threshold in steps of 0.1 Volts."
    ::= { ovaMeasuringValuesEntry 61 }

    ovaPlus5VLo OBJECT-TYPE
        SYNTAX INTEGER
        ACCESS read-only
        STATUS mandatory
        DESCRIPTION "The 5V supply voltage low warning threshold in steps of 0.1 Volts."
    ::= { ovaMeasuringValuesEntry 62 }

    ovaPlus5VValue OBJECT-TYPE
        SYNTAX INTEGER
        ACCESS read-only
        STATUS mandatory
        DESCRIPTION "The 5V supply voltage in steps of 0.1 Volts."
    ::= { ovaMeasuringValuesEntry 63 }

    ovaPlus5VHi OBJECT-TYPE
        SYNTAX INTEGER
        ACCESS read-only
        STATUS mandatory
        DESCRIPTION "The 5V supply voltage high warning threshold in steps of 0.1 Volts."
    ::= { ovaMeasuringValuesEntry 64 }

    ovaPlus5VHiHi OBJECT-TYPE
        SYNTAX INTEGER
        ACCESS read-only
        STATUS mandatory
        DESCRIPTION "The 5V supply voltage high alarm threshold in steps of 0.1 Volts."
    ::= { ovaMeasuringValuesEntry 65 }

-- *****
    ovaPlus10VLoLo OBJECT-TYPE
        SYNTAX INTEGER
        ACCESS read-only
        STATUS mandatory
        DESCRIPTION "The 10V supply voltage low alarm threshold in steps of 0.1 Volts."
    ::= { ovaMeasuringValuesEntry 66 }

    ovaPlus10VLo OBJECT-TYPE
        SYNTAX INTEGER
        ACCESS read-only
        STATUS mandatory
        DESCRIPTION "The 10V supply voltage low warning threshold in steps of 0.1 Volts."
    ::= { ovaMeasuringValuesEntry 67 }

    ovaPlus10VValue OBJECT-TYPE
        SYNTAX INTEGER
        ACCESS read-only
        STATUS mandatory
        DESCRIPTION "The 10V supply voltage in steps of 0.1 Volts."
    ::= { ovaMeasuringValuesEntry 68 }

    ovaPlus10VHi OBJECT-TYPE
        SYNTAX INTEGER
        ACCESS read-only
        STATUS mandatory
        DESCRIPTION "The 10V supply voltage high warning threshold in steps of 0.1 Volts."
    ::= { ovaMeasuringValuesEntry 69 }

    ovaPlus10VHiHi OBJECT-TYPE
        SYNTAX INTEGER
        ACCESS read-only
        STATUS mandatory
        DESCRIPTION "The 10V supply voltage high alarm threshold in steps of 0.1 Volts."
    ::= { ovaMeasuringValuesEntry 70 }

-- *****
    ovaPlus24VLoLo OBJECT-TYPE
        SYNTAX INTEGER
        ACCESS read-only
        STATUS mandatory
        DESCRIPTION "The 24V supply voltage low alarm threshold in steps of 0.1 Volts."
    ::= { ovaMeasuringValuesEntry 71 }

    ovaPlus24VLo OBJECT-TYPE
        SYNTAX INTEGER
        ACCESS read-only
        STATUS mandatory
        DESCRIPTION "The 24V supply voltage low warning threshold in steps of 0.1 Volts."
    ::= { ovaMeasuringValuesEntry 72 }

    ovaPlus24VValue OBJECT-TYPE
        SYNTAX INTEGER
        ACCESS read-only
        STATUS mandatory
        DESCRIPTION "The 24V supply voltage in steps of 0.1 Volts."
    ::= { ovaMeasuringValuesEntry 73 }

    ovaPlus24VHi OBJECT-TYPE
        SYNTAX INTEGER
        ACCESS read-only
        STATUS mandatory
        DESCRIPTION "The 24V supply voltage high warning threshold in steps of 0.1 Volts."
    ::= { ovaMeasuringValuesEntry 74 }

    ovaPlus24VHiHi OBJECT-TYPE
        SYNTAX INTEGER
        ACCESS read-only
        STATUS mandatory
        DESCRIPTION "The 24V supply voltage high alarm threshold in steps of 0.1 Volts."
    ::= { ovaMeasuringValuesEntry 75 }

-- *****
    ovaTemperatureLoLo OBJECT-TYPE
        SYNTAX INTEGER
        ACCESS read-only
        STATUS mandatory
        DESCRIPTION "The module temperature low alarm threshold in steps of 0.1 celsius degrees."
    ::= { ovaMeasuringValuesEntry 76 }

    ovaTemperatureLo OBJECT-TYPE
        SYNTAX INTEGER
        ACCESS read-only
        STATUS mandatory
        DESCRIPTION "The module temperature low warning threshold in steps of 0.1 celsius degrees."
    ::= { ovaMeasuringValuesEntry 77 }

    ovaTemperatureValue OBJECT-TYPE
        SYNTAX INTEGER
        ACCESS read-only
        STATUS mandatory
        DESCRIPTION "The module temperature in steps of 0.1 celsius degrees."
    ::= { ovaMeasuringValuesEntry 78 }

    ovaTemperatureHi OBJECT-TYPE
        SYNTAX INTEGER
        ACCESS read-only
        STATUS mandatory
        DESCRIPTION "The module temperature high warning threshold in steps of 0.1 celsius degrees."
    ::= { ovaMeasuringValuesEntry 79 }

    ovaTemperatureHiHi OBJECT-TYPE
        SYNTAX INTEGER
        ACCESS read-only
        STATUS mandatory
        DESCRIPTION "The module temperature high alarm threshold in steps of 0.1 celsius degrees."
    ::= { ovaMeasuringValuesEntry 80 }

-- *****
    ovaReturnLossLoLo OBJECT-TYPE
        SYNTAX INTEGER
        ACCESS read-only
        STATUS mandatory
        DESCRIPTION "ReturnLoss low alarm threshold in steps of 0.1 dB."
    ::= { ovaMeasuringValuesEntry 81 }

    ovaReturnLossLo OBJECT-TYPE
        SYNTAX INTEGER
        ACCESS read-only
        STATUS mandatory
        DESCRIPTION "ReturnLoss low warning threshold in steps of 0.1 dB."
    ::= { ovaMeasuringValuesEntry 82 }

    ovaReturnLossValue OBJECT-TYPE
        SYNTAX INTEGER
        ACCESS read-only
        STATUS mandatory
        DESCRIPTION "ReturnLoss in steps of 0.1 dB."
    ::= { ovaMeasuringValuesEntry 83 }

    ovaReturnLossHi OBJECT-TYPE
        SYNTAX INTEGER
        ACCESS read-only
        STATUS mandatory
        DESCRIPTION "ReturnLoss high warning threshold in steps of 0.1 dB."
    ::= { ovaMeasuringValuesEntry 84 }

    ovaReturnLossHiHi OBJECT-TYPE
        SYNTAX INTEGER
        ACCESS read-only
        STATUS mandatory
        DESCRIPTION "ReturnLoss  high alarm threshold in steps of 0.1 dB."
    ::= { ovaMeasuringValuesEntry 85 }


--*****************************************************************************************
--  ovaStates group

    ovaStatesTable OBJECT-TYPE
        SYNTAX SEQUENCE OF OvaStatesEntry
        ACCESS not-accessible
        STATUS mandatory
        DESCRIPTION ""
    ::= { ovaStates 1 }

-- table of states entry(ro/rw)

    ovaStatesEntry OBJECT-TYPE
        SYNTAX OvaStatesEntry
        ACCESS not-accessible
        STATUS mandatory
        DESCRIPTION "Alarms for a module."
        INDEX { ovaNESlot }
    ::= { ovaStatesTable 1 }

-- the structure of the entry

    OvaStatesEntry ::= SEQUENCE
    {
        ovaStatesSystem             PerceivedSeverityValue,
        ovaStatesOutputLow          PerceivedSeverityValue,
        ovaStatesOutputHigh         PerceivedSeverityValue,
        ovaStatesInputLow           PerceivedSeverityValue,
        ovaStatesInputHigh          PerceivedSeverityValue,
        ovaStatesLaserAging         PerceivedSeverityValue,
        ovaStatesTecHigh            PerceivedSeverityValue,
        ovaStatesPowerSupplyLeft    PerceivedSeverityValue,
        ovaStatesPowerSupplyRight   PerceivedSeverityValue,
        ovaStatesFanLeft            PerceivedSeverityValue,
        ovaStatesFanRight           PerceivedSeverityValue,
        ovaStatesTemperatureLow     PerceivedSeverityValue,
        ovaStatesTemperatureHigh    PerceivedSeverityValue,
        ovaStatesLaserTempLow       PerceivedSeverityValue,
        ovaStatesLaserTempHigh      PerceivedSeverityValue,
        ovaStatesLaserPlus3p3VLow   PerceivedSeverityValue,
        ovaStatesLaserPlus3p3VHigh  PerceivedSeverityValue,
        ovaStatesPlus3p3VLow        PerceivedSeverityValue,
        ovaStatesPlus3p3VHigh       PerceivedSeverityValue,
        ovaStatesPlus5VLow          PerceivedSeverityValue,
        ovaStatesPlus5VHigh         PerceivedSeverityValue,
        ovaStatesPlus10VLow         PerceivedSeverityValue,
        ovaStatesPlus10VHigh        PerceivedSeverityValue,
        ovaStatesPlus24VLow         PerceivedSeverityValue,
        ovaStatesPlus24VHigh        PerceivedSeverityValue,
        ovaStatesLaserShutdown      PerceivedSeverityValue,
        ovaStatesInitializing       PerceivedSeverityValue,
        ovaStatesBootloader         PerceivedSeverityValue,
        ovaStatesDefective          PerceivedSeverityValue,
        ovaStatesRedundancySwitch   PerceivedSeverityValue,
        ovaStatesReturnLossLow      PerceivedSeverityValue,
        ovaStatesReturnLossHigh     PerceivedSeverityValue
    }

    ovaStatesSystem OBJECT-TYPE
        SYNTAX PerceivedSeverityValue
        ACCESS read-only
        STATUS mandatory
        DESCRIPTION "Internal error occured"
    ::= { ovaStatesEntry 1 }

    ovaStatesOutputLow OBJECT-TYPE
        SYNTAX PerceivedSeverityValue
        ACCESS read-only
        STATUS mandatory
        DESCRIPTION "Optical output power (or gain) low"
    ::= { ovaStatesEntry 2 }

    ovaStatesOutputHigh OBJECT-TYPE
        SYNTAX PerceivedSeverityValue
        ACCESS read-only
        STATUS mandatory
        DESCRIPTION "Optical output power (or gain) high"
    ::= { ovaStatesEntry 3 }

    ovaStatesInputLow OBJECT-TYPE
        SYNTAX PerceivedSeverityValue
        ACCESS read-only
        STATUS mandatory
        DESCRIPTION "Optical input power low"
    ::= { ovaStatesEntry 4 }

    ovaStatesInputHigh OBJECT-TYPE
        SYNTAX PerceivedSeverityValue
        ACCESS read-only
        STATUS mandatory
        DESCRIPTION "Optical input power high"
    ::= { ovaStatesEntry 5 }

    ovaStatesLaserAging OBJECT-TYPE
        SYNTAX PerceivedSeverityValue
        ACCESS read-only
        STATUS mandatory
        DESCRIPTION "The laser is aging"
    ::= { ovaStatesEntry 6 }

    ovaStatesTecHigh OBJECT-TYPE
        SYNTAX PerceivedSeverityValue
        ACCESS read-only
        STATUS mandatory
        DESCRIPTION "Laser cooler limit reached"
    ::= { ovaStatesEntry 7 }

    ovaStatesPowerSupplyLeft OBJECT-TYPE
        SYNTAX PerceivedSeverityValue
        ACCESS read-only
        STATUS mandatory
        DESCRIPTION "The left (looking from front) power supply unit fails"
    ::= { ovaStatesEntry 8 }

    ovaStatesPowerSupplyRight OBJECT-TYPE
        SYNTAX PerceivedSeverityValue
        ACCESS read-only
        STATUS mandatory
        DESCRIPTION "The right (looking from front) power supply unit fails"
    ::= { ovaStatesEntry 9 }

    ovaStatesFanLeft OBJECT-TYPE
        SYNTAX PerceivedSeverityValue
        ACCESS read-only
        STATUS mandatory
        DESCRIPTION "The left (looking from front) fan unit fails"
    ::= { ovaStatesEntry 10 }

    ovaStatesFanRight OBJECT-TYPE
        SYNTAX PerceivedSeverityValue
        ACCESS read-only
        STATUS mandatory
        DESCRIPTION "The right (looking from front) fan unit fails"
    ::= { ovaStatesEntry 11 }

    ovaStatesTemperatureLow OBJECT-TYPE
        SYNTAX PerceivedSeverityValue
        ACCESS read-only
        STATUS mandatory
        DESCRIPTION "Device internal temperature low"
    ::= { ovaStatesEntry 12 }

    ovaStatesTemperatureHigh OBJECT-TYPE
        SYNTAX PerceivedSeverityValue
        ACCESS read-only
        STATUS mandatory
        DESCRIPTION "Device internal temperature high"
    ::= { ovaStatesEntry 13 }

    ovaStatesLaserTempLow OBJECT-TYPE
        SYNTAX PerceivedSeverityValue
        ACCESS read-only
        STATUS mandatory
        DESCRIPTION "Laser temperature low"
    ::= { ovaStatesEntry 14 }

    ovaStatesLaserTempHigh OBJECT-TYPE
        SYNTAX PerceivedSeverityValue
        ACCESS read-only
        STATUS mandatory
        DESCRIPTION "Laser temperature high"
    ::= { ovaStatesEntry 15 }

    ovaStatesLaserPlus3p3VLow OBJECT-TYPE
        SYNTAX PerceivedSeverityValue
        ACCESS read-only
        STATUS mandatory
        DESCRIPTION "Laser 3.3 Volt supply low"
    ::= { ovaStatesEntry 16 }

    ovaStatesLaserPlus3p3VHigh OBJECT-TYPE
        SYNTAX PerceivedSeverityValue
        ACCESS read-only
        STATUS mandatory
        DESCRIPTION "Laser 3.3 Volt supply high"
    ::= { ovaStatesEntry 17 }

    ovaStatesPlus3p3VLow OBJECT-TYPE
        SYNTAX PerceivedSeverityValue
        ACCESS read-only
        STATUS mandatory
        DESCRIPTION "3.3 Volt supply low"
    ::= { ovaStatesEntry 18 }

    ovaStatesPlus3p3VHigh OBJECT-TYPE
        SYNTAX PerceivedSeverityValue
        ACCESS read-only
        STATUS mandatory
        DESCRIPTION "3.3 Volt supply high"
    ::= { ovaStatesEntry 19 }

    ovaStatesPlus5VLow OBJECT-TYPE
        SYNTAX PerceivedSeverityValue
        ACCESS read-only
        STATUS mandatory
        DESCRIPTION "5 Volt supply low"
    ::= { ovaStatesEntry 20 }

    ovaStatesPlus5VHigh OBJECT-TYPE
        SYNTAX PerceivedSeverityValue
        ACCESS read-only
        STATUS mandatory
        DESCRIPTION "5 Volt supply high"
    ::= { ovaStatesEntry 21 }

    ovaStatesPlus10VLow OBJECT-TYPE
        SYNTAX PerceivedSeverityValue
        ACCESS read-only
        STATUS mandatory
        DESCRIPTION "10 Volt supply low"
    ::= { ovaStatesEntry 22 }

    ovaStatesPlus10VHigh OBJECT-TYPE
        SYNTAX PerceivedSeverityValue
        ACCESS read-only
        STATUS mandatory
        DESCRIPTION "10 Volt supply high"
    ::= { ovaStatesEntry 23 }

    ovaStatesPlus24VLow OBJECT-TYPE
        SYNTAX PerceivedSeverityValue
        ACCESS read-only
        STATUS mandatory
        DESCRIPTION "24 Volt supply low"
    ::= { ovaStatesEntry 24 }

    ovaStatesPlus24VHigh OBJECT-TYPE
        SYNTAX PerceivedSeverityValue
        ACCESS read-only
        STATUS mandatory
        DESCRIPTION "24 Volt supply high"
    ::= { ovaStatesEntry 25 }

    ovaStatesLaserShutdown OBJECT-TYPE
        SYNTAX PerceivedSeverityValue
        ACCESS read-only
        STATUS mandatory
        DESCRIPTION "Lasers are shutdown, no optical output"
    ::= { ovaStatesEntry 26 }

    ovaStatesInitializing OBJECT-TYPE
        SYNTAX PerceivedSeverityValue
        ACCESS read-only
        STATUS mandatory
        DESCRIPTION "The device is initializing"
    ::= { ovaStatesEntry 27 }

    ovaStatesBootloader OBJECT-TYPE
        SYNTAX PerceivedSeverityValue
        ACCESS read-only
        STATUS mandatory
        DESCRIPTION 
            "The device is running in bootloader mode 
             without a legal application software." 
    ::= { ovaStatesEntry 28 }

    ovaStatesDefective OBJECT-TYPE
        SYNTAX PerceivedSeverityValue
        ACCESS read-only
        STATUS mandatory
        DESCRIPTION
            "The NEC has lost the connection to the device. 
             Reason may be a removed or defective device.
             Note that this state is set by the NEC and not 
             by the device" 
    ::= { ovaStatesEntry 29 }

    ovaStatesRedundancySwitch OBJECT-TYPE
        SYNTAX PerceivedSeverityValue
        ACCESS read-only
        STATUS mandatory
        DESCRIPTION "This (redundant) device has been activated (redundancy switchover)"
    ::= { ovaStatesEntry 30 }

    ovaStatesReturnLossLow OBJECT-TYPE
        SYNTAX PerceivedSeverityValue
        ACCESS read-only
        STATUS mandatory
        DESCRIPTION "Return loss low"
    ::= { ovaStatesEntry 31 }

    ovaStatesReturnLossHigh OBJECT-TYPE
        SYNTAX PerceivedSeverityValue
        ACCESS read-only
        STATUS mandatory
        DESCRIPTION "Return loss high"
    ::= { ovaStatesEntry 32 }


--*****************************************************************************************
--  ovaControl group

  ovaControlTable OBJECT-TYPE
    SYNTAX SEQUENCE OF OvaControlEntry
    ACCESS not-accessible
    STATUS mandatory
    DESCRIPTION ""
  ::= { ovaControl 1 }

-- table of control entry(ro/rw)

  ovaControlEntry OBJECT-TYPE
    SYNTAX OvaControlEntry
    ACCESS not-accessible
    STATUS mandatory
    DESCRIPTION "Alarms for a module."
    INDEX { ovaNESlot }
  ::= { ovaControlTable 1 }

-- the structure of the entry

    OvaControlEntry ::= SEQUENCE
    {
        ovaControlLaserShutdown                     TruthValue,
        ovaControlReset                             TruthValue,
        ovaControlModuleLedBlink                    TruthValue,
        ovaControlSbsEvaluationStart                TruthValue
    }

    ovaControlLaserShutdown OBJECT-TYPE
        SYNTAX TruthValue
        ACCESS read-write
        STATUS mandatory
        DESCRIPTION "Shutdown the laser(s), optical power on/off."
    ::= { ovaControlEntry 1 }

    ovaControlReset OBJECT-TYPE
      SYNTAX TruthValue
      ACCESS read-write
      STATUS mandatory
      DESCRIPTION "Reset the module."
    ::= { ovaControlEntry 2 }

    ovaControlModuleLedBlink OBJECT-TYPE
        SYNTAX TruthValue
        ACCESS read-write
        STATUS mandatory
        DESCRIPTION   "Writing this variable to true(1) lets the device's 
        modul LED blink green for 10 seconds. 
        Writing this variable to false(2) stops blinking at once.
        This variable always returns false(2) on read requests"
    ::= { ovaControlEntry 3 }

    ovaControlSbsEvaluationStart OBJECT-TYPE
        SYNTAX TruthValue
        ACCESS read-write
        STATUS mandatory
        DESCRIPTION
            "Setting to true(1) starts an SBS threshold evaluation process.
             Always reads as false(2)"
    ::={ ovaControlEntry 4 }


--*****************************************************************************************
-- ovaConfiguration group

    ovaConfigurationTable OBJECT-TYPE
        SYNTAX SEQUENCE OF OvaConfigurationEntry
        ACCESS not-accessible
        STATUS mandatory
        DESCRIPTION ""
    ::= { ovaConfiguration 1 }

-- table of configuration entry(ro/rw)

    ovaConfigurationEntry OBJECT-TYPE
        SYNTAX OvaConfigurationEntry
        ACCESS not-accessible
        STATUS mandatory
        DESCRIPTION ""
        INDEX { ovaNESlot  }
    ::= { ovaConfigurationTable 1 }

-- the structure of the entry

    OvaConfigurationEntry ::= SEQUENCE
    {
        ovaConfigNESlotWrite                     NESlotWriteValue,
        ovaConfigRegulationMode                  RegulationMode,
        ovaConfigOutputPwrOrGainAdjust           INTEGER,
        ovaConfigInputPwrLimitLoLo               INTEGER,
        ovaConfigInputPwrLimitLo                 INTEGER,
        ovaConfigInputPwrLimitHi                 INTEGER,
        ovaConfigInputPwrLimitHiHi               INTEGER,
        ovaConfigOutputPwrOrGainLimitLoLo        INTEGER,
        ovaConfigOutputPwrOrGainLimitLo          INTEGER,
        ovaConfigOutputPwrOrGainLimitHi          INTEGER,
        ovaConfigOutputPwrOrGainLimitHiHi        INTEGER,
        ovaConfigModeExtIO                       ExtIOmode,
        ovaConfigMaskExtIO                       ExtIOmask,
        ovaConfigSbsEvaluationMode               SbsEvaluationMode
    }

    ovaConfigNESlotWrite OBJECT-TYPE
        SYNTAX NESlotWriteValue
        ACCESS read-write
        STATUS optional
        DESCRIPTION "By writing this variable a slot can be assigned
            for devices that dont support hardware slot detection.
            Reading '-1' means that the slot position is NOT writable."
    ::= { ovaConfigurationEntry 1 }

    ovaConfigRegulationMode OBJECT-TYPE
        SYNTAX  RegulationMode
        ACCESS  read-write
        STATUS  mandatory
        DESCRIPTION
            "The regulation mode of the device.
             - regModeConstantOutputPower(1):
               If the device runs in constant output power mode, then all *OutputPwrOrGain*
               variables are interpreted as 'Output Power' specific.
             - regModeConstantGain(2):
               If the device runs in constant gain mode, then all *OutputPwrOrGain*
               variables are interpreted as 'Gain' specific."
    ::={ ovaConfigurationEntry 2 }

    ovaConfigOutputPwrOrGainAdjust OBJECT-TYPE
        SYNTAX  INTEGER
        ACCESS  read-write
        STATUS  mandatory
        DESCRIPTION
            "This variable can be used to adjust the desired output power (or gain) 
             value in 0.1 dB(m) units.
             See ovaConfigRegulationMode variable too"
    ::={ ovaConfigurationEntry 3 }

    ovaConfigInputPwrLimitLoLo OBJECT-TYPE
        SYNTAX  INTEGER
        ACCESS  read-write
        STATUS  mandatory
        DESCRIPTION
            "The optical input power low alarm limit in 0.1 dBm units"
    ::={ ovaConfigurationEntry 4 }

    ovaConfigInputPwrLimitLo OBJECT-TYPE
        SYNTAX  INTEGER
        ACCESS  read-write
        STATUS  mandatory
        DESCRIPTION
            "The optical input power low warning limit in 0.1 dBm units"
    ::={ ovaConfigurationEntry 5 }

    ovaConfigInputPwrLimitHi OBJECT-TYPE
        SYNTAX  INTEGER
        ACCESS  read-write
        STATUS  mandatory
        DESCRIPTION
            "The optical input power high warning limit in 0.1 dBm units"
    ::={ ovaConfigurationEntry 6 }

    ovaConfigInputPwrLimitHiHi OBJECT-TYPE
        SYNTAX  INTEGER
        ACCESS  read-write
        STATUS  mandatory
        DESCRIPTION
            "The optical input power high alarm limit in 0.1 dBm units"
    ::={ ovaConfigurationEntry 7 }

    ovaConfigOutputPwrOrGainLimitLoLo OBJECT-TYPE
        SYNTAX  INTEGER
        ACCESS  read-write
        STATUS  mandatory
        DESCRIPTION
            "The output power (or gain) low alarm limit in 0.1 dBm units (relative to adjusted output power or gain)"
    ::={ ovaConfigurationEntry 8 }

    ovaConfigOutputPwrOrGainLimitLo OBJECT-TYPE
        SYNTAX  INTEGER
        ACCESS  read-write
        STATUS  mandatory
        DESCRIPTION
            "The output power (or gain) low warning limit in 0.1 dBm units (relative to adjusted output power or gain)"
    ::={ ovaConfigurationEntry 9 }

    ovaConfigOutputPwrOrGainLimitHi OBJECT-TYPE
        SYNTAX  INTEGER
        ACCESS  read-write
        STATUS  mandatory
        DESCRIPTION
            "The output power (or gain) high warning limit in 0.1 dBm units (relative to adjusted output power or gain)"
    ::={ ovaConfigurationEntry 10 }

    ovaConfigOutputPwrOrGainLimitHiHi OBJECT-TYPE
        SYNTAX  INTEGER
        ACCESS  read-write
        STATUS  mandatory
        DESCRIPTION
            "The output power (or gain) high alarm limit in 0.1 dBm units (relative to adjusted output power or gain)"
    ::={ ovaConfigurationEntry 11 }

    ovaConfigModeExtIO OBJECT-TYPE
        SYNTAX ExtIOmode
        ACCESS read-write
        STATUS mandatory
        DESCRIPTION   "The mode and usage of the device's external IO port."
    ::= { ovaConfigurationEntry 12 }

    ovaConfigMaskExtIO OBJECT-TYPE
        SYNTAX ExtIOmask
        ACCESS read-write
        STATUS mandatory
        DESCRIPTION   
          "The alarm/warning mask that activates the device's external IO port."
    ::= { ovaConfigurationEntry 13 }

    ovaConfigSbsEvaluationMode OBJECT-TYPE
        SYNTAX SbsEvaluationMode
        ACCESS read-write
        STATUS mandatory
        DESCRIPTION
            "The SBS threshold evaluation mode."
    ::={ ovaConfigurationEntry 14 }

--*****************************************************************************************
-- Display group

    ovaDisplayTable OBJECT-TYPE
        SYNTAX SEQUENCE OF OvaDisplayEntry
        ACCESS not-accessible
        STATUS mandatory
        DESCRIPTION ""
    ::= { ovaDisplay 1 }

-- table of configuration entry(ro/rw)

    ovaDisplayEntry OBJECT-TYPE
        SYNTAX OvaDisplayEntry
        ACCESS not-accessible
        STATUS mandatory
        DESCRIPTION ""
        INDEX { ovaNESlot  }
    ::= { ovaDisplayTable 1 }

-- the structure of the entry

    OvaDisplayEntry ::= SEQUENCE
    {
        ovaDisplayLaserCount                INTEGER,
        ovaDisplayOutputPwrOrGainAdjustMin  INTEGER,
        ovaDisplayOutputPwrOrGainAdjustMax  INTEGER,
        ovaDisplayOutputPwrOrGainAdjustStep INTEGER,
        ovaDisplayLaser1PumpPowerRel        INTEGER,
        ovaDisplayLaser2PumpPowerRel        INTEGER,
        ovaDisplayOutputPwrOrGainNominal    INTEGER,
        ovaDisplaySbsEvaluatedThreshold     INTEGER,
        ovaDisplaySbsLastEvaluationState    SbsEvaluationState,
        ovaDisplaySbsLastEvaluationTime     DisplayString
    }

    ovaDisplayLaserCount OBJECT-TYPE
        SYNTAX  INTEGER
        ACCESS  read-only
        STATUS  mandatory
        DESCRIPTION
            "The number of lasers used by this optical amplifier"
    ::={ ovaDisplayEntry 1 }

    ovaDisplayOutputPwrOrGainAdjustMin OBJECT-TYPE
        SYNTAX  INTEGER
        ACCESS  read-only
        STATUS  mandatory
        DESCRIPTION
            "The minimum adjustable offset from nominal output power (or gain) in 0.1 dB(m) units.
             See ovaConfigRegulationMode variable too"
    ::={ ovaDisplayEntry 2 }

    ovaDisplayOutputPwrOrGainAdjustMax OBJECT-TYPE
        SYNTAX  INTEGER
        ACCESS  read-only
        STATUS  mandatory
        DESCRIPTION
            "The maximum adjustable offset from nominal output power (or gain) in 0.1 dB(m) units.
             See ovaConfigRegulationMode variable too"
    ::={ ovaDisplayEntry 3 }

    ovaDisplayOutputPwrOrGainAdjustStep OBJECT-TYPE
        SYNTAX  INTEGER
        ACCESS  read-only
        STATUS  mandatory
        DESCRIPTION
            "The stepsize that can be used to adjust the output power (or gain) in 0.1 dB units.
             See ovaConfigRegulationMode variable too"
    ::={ ovaDisplayEntry 4 }

    ovaDisplayLaser1PumpPowerRel OBJECT-TYPE
        SYNTAX  INTEGER
        ACCESS  read-only
        STATUS  mandatory
        DESCRIPTION
            "The pump power of laser no.1 in percent"
    ::={ ovaDisplayEntry 5 }

    ovaDisplayLaser2PumpPowerRel OBJECT-TYPE
        SYNTAX  INTEGER
        ACCESS  read-only
        STATUS  mandatory
        DESCRIPTION
            "The pump power of laser no.2 in percent"
    ::={ ovaDisplayEntry 6 }

    ovaDisplayOutputPwrOrGainNominal OBJECT-TYPE
        SYNTAX  INTEGER
        ACCESS  read-only
        STATUS  mandatory
        DESCRIPTION
            "The nominal output power (or gain) in 0.1 dB(m) units.
             See ovaConfigRegulationMode variable too"
    ::={ ovaDisplayEntry 7 }

    ovaDisplaySbsEvaluatedThreshold OBJECT-TYPE
        SYNTAX  INTEGER
        ACCESS  read-only
        STATUS  mandatory
        DESCRIPTION
            "The evaluated SBS output power or gain threshold in 0.1 dB(m) units.
             Not supported by all optical amplifiers"
    ::={ ovaDisplayEntry 8 }

    ovaDisplaySbsLastEvaluationState OBJECT-TYPE
        SYNTAX  SbsEvaluationState
        ACCESS  read-only
        STATUS  mandatory
        DESCRIPTION
            "The result of last SBS threshold evaluation process.
             Returns 'evaluationNotSupported(1)' if SBS threshold evaluation 
             is not supported by this optical amplifier"
    ::={ ovaDisplayEntry 9 }

    ovaDisplaySbsLastEvaluationTime OBJECT-TYPE
        SYNTAX  DisplayString
        ACCESS  read-only
        STATUS  mandatory
        DESCRIPTION
            "The time of last successfull SBS threshold evaluation process.
             Not supported by all optical amplifiers"
    ::={ ovaDisplayEntry 10 }


--*****************************************************************************************
END
