--- ****************************************************************************
-- *
-- * Description:   Implements definitions for the Otr-modul
-- *                (Optical Transceiver (BOX860) design release V01)
-- *
-- * Copyright 2003 by BKtel communications GmbH
-- *
-- *
-- *     V.0.1 17.06.03  M. Heldmann    first draft
-- *     V.0.2 23.07.03  M. Heldmann    ledsActiveOnlyIfLidClosed changed to ledsActiveOnlyIfLidOpen
-- *                                    added descriptions for the states
-- *     V.0.3 07.01.04  M. Heldmann    added 'otrConfigOutputVoltageOffset'
-- *     V.0.4 06.04.04  M. Heldmann    changed description for 'otrConfigOutputVoltageOffset'
-- *     V.0.5 04.10.06  M. Heldmann    NESlotWriteValue expanded due to new 2G6 platform needs
-- *     V.0.6 29.05.08  M. Heldmann    renamed threshold parameters in xxxxMeasuringValuesTable
-- *     V.0.7 11.07.13  M. Heldmann    adjusted syntax of "CommonEntry" to remove MIB compiler warnings
-- *     V.0.8 05.09.14  M. Heldmann    changed CommonModuleWidth and ConfigNESlotWrite STATUS to optional
-- ****************************************************************************

BKTEL-HFC862-OTR-V01-MIB DEFINITIONS ::= BEGIN

    IMPORTS
        experimental, enterprises, TimeTicks, IpAddress, Counter
                 FROM RFC1155-SMI
    OBJECT-TYPE
                 FROM RFC-1212
        TRAP-TYPE
                 FROM RFC-1215
        modules, DisplayString, TruthValue, PerceivedSeverityValue, NESlotValue, ModuleWidthValue
                 FROM   BKTEL-HFC862-BASE-MIB
    ;

    otr                 OBJECT IDENTIFIER ::= { modules 107 }
    otrCommon           OBJECT IDENTIFIER ::= { otr 1 }
    otrStates           OBJECT IDENTIFIER ::= { otr 2 }
    otrConfiguration    OBJECT IDENTIFIER ::= { otr 3 }
    otrControl          OBJECT IDENTIFIER ::= { otr 4 }
    otrMeasuringValues  OBJECT IDENTIFIER ::= { otr 5 }
    otrDisplay          OBJECT IDENTIFIER ::= { otr 6 }


--
-- Type definitions
--

        NESlotWriteValue ::= INTEGER (-1..99)

        LedActivityValue ::= INTEGER
            {
            ledsAlwaysActive(1),
            ledsActiveOnlyIfLidOpen(2)
            }

        AuxRfOutputModeValue ::= INTEGER
            {
            dcRemoteControlled(1),
            alwaysOn(2),
            alwaysOff(3)
            }

        AuxRfInputModeValue ::= INTEGER
            {
            followReceiversAuxOutput(1),
            alwaysOn(2),
            alwaysOff(3)
            }

        OptOutputModeValue ::= INTEGER
            {
            optOutputNominal(1),
            optOutputSleep(2)
            }

        LineCodeNumberValue ::= INTEGER (0..999)

        LineCodeNomRedFlagValue ::= INTEGER
            {
            sendNominalFlag(1),
            sendRedundantFlag(2)
            }


--*****************************************************************************************
-- OTR (Optical Transceiver (BOX860) design release V01)

--*****************************************************************************************
-- otrCommon group

    otrCommonNumberOfModules OBJECT-TYPE
        SYNTAX  INTEGER(0..50)
        ACCESS  read-only
        STATUS  mandatory
        DESCRIPTION "Number of modules in table."
  ::= { otrCommon 1 }

    otrCommonTable OBJECT-TYPE
        SYNTAX SEQUENCE OF OtrCommonEntry
        ACCESS not-accessible
        STATUS mandatory
        DESCRIPTION "The table contains all modules of the OTR-type in the NE"
  ::= { otrCommon 2 }

-- table of states entry(ro/rw)

    otrCommonEntry OBJECT-TYPE
        SYNTAX OtrCommonEntry
        ACCESS not-accessible
        STATUS mandatory
        DESCRIPTION "Common-Values for a module."
        INDEX { otrNESlot }
  ::= { otrCommonTable 1 }

-- the structure of the entry

    OtrCommonEntry ::= SEQUENCE
    {
        otrNESlot                      NESlotValue,
        otrCommonType                  DisplayString,
        otrCommonDescr                 DisplayString,
        otrCommonFirmwareId            DisplayString,
        otrCommonModuleWidth           ModuleWidthValue
    }

    otrNESlot OBJECT-TYPE
        SYNTAX  NESlotValue
        ACCESS  read-only
        STATUS  mandatory
        DESCRIPTION
        "The slot number of the chassis for which this
        entry contains management information."
    ::= { otrCommonEntry 1 }

    otrCommonType OBJECT-TYPE
        SYNTAX  DisplayString  (SIZE(0..32))
        ACCESS  read-only
        STATUS  mandatory
        DESCRIPTION
        "The type of physical module. modSlotEmpty indicates
         an empty slot.  A Value of modSlotUnknown indicates
         that the type of module is unknown."
    ::= { otrCommonEntry 2 }

    otrCommonDescr OBJECT-TYPE
        SYNTAX  DisplayString
        ACCESS  read-write
        STATUS  mandatory
        DESCRIPTION
        "A textual description of the module.
        If not available, this Value should be
        set to a zero length string."
    ::= { otrCommonEntry 3 }

    otrCommonFirmwareId OBJECT-TYPE
        SYNTAX DisplayString (SIZE(0..32))
        ACCESS read-only
        STATUS mandatory
        DESCRIPTION "The firmware Id of the module."
    ::= { otrCommonEntry 4 }

    otrCommonModuleWidth OBJECT-TYPE
        SYNTAX ModuleWidthValue
        ACCESS read-only
        STATUS optional
        DESCRIPTION "The width of the module in multiples of slots (1, 2, ...)"
    ::= { otrCommonEntry 5 }

--*****************************************************************************************
-- otrMeasuringValues group

-- table of measuring Values

    otrMeasuringValuesTable OBJECT-TYPE
        SYNTAX SEQUENCE OF OtrMeasuringValuesEntry
        ACCESS not-accessible
        STATUS mandatory
        DESCRIPTION ""
   ::= { otrMeasuringValues 1 }

-- table of measuring Values entry

    otrMeasuringValuesEntry OBJECT-TYPE
        SYNTAX OtrMeasuringValuesEntry
        ACCESS not-accessible
        STATUS mandatory
        DESCRIPTION "Common-Values for a module."
        INDEX { otrNESlot }
  ::= { otrMeasuringValuesTable 1 }

--  the structure of the entry

    OtrMeasuringValuesEntry ::= SEQUENCE
    {
        otrInputPowerLoLo             INTEGER,
        otrInputPowerLo               INTEGER,
        otrInputPowerValue            INTEGER,
        otrInputPowerHi               INTEGER,
        otrInputPowerHiHi             INTEGER,

        otrOutputPowerLoLo            INTEGER,
        otrOutputPowerLo              INTEGER,
        otrOutputPowerValue           INTEGER,
        otrOutputPowerHi              INTEGER,
        otrOutputPowerHiHi            INTEGER,

        otrLaserCurrentRelLoLo        INTEGER,
        otrLaserCurrentRelLo          INTEGER,
        otrLaserCurrentRelValue       INTEGER,
        otrLaserCurrentRelHi          INTEGER,
        otrLaserCurrentRelHiHi        INTEGER,

        otrPlus24VLoLo                INTEGER,
        otrPlus24VLo                  INTEGER,
        otrPlus24VValue               INTEGER,
        otrPlus24VHi                  INTEGER,
        otrPlus24VHiHi                INTEGER,

        otrTemperatureLoLo            INTEGER,
        otrTemperatureLo              INTEGER,
        otrTemperatureValue           INTEGER,
        otrTemperatureHi              INTEGER,
        otrTemperatureHiHi            INTEGER
    }

-- *****
    otrInputPowerLoLo OBJECT-TYPE
        SYNTAX INTEGER
        ACCESS read-only
        STATUS mandatory
        DESCRIPTION "Input power low alarm threshold in steps of 0.1dBm."
    ::= { otrMeasuringValuesEntry 1 }

    otrInputPowerLo OBJECT-TYPE
        SYNTAX INTEGER
        ACCESS read-only
        STATUS mandatory
        DESCRIPTION "Input power low warning threshold in steps of 0.1dBm."
    ::= { otrMeasuringValuesEntry 2 }

    otrInputPowerValue OBJECT-TYPE
        SYNTAX INTEGER
        ACCESS read-only
        STATUS mandatory
        DESCRIPTION "Input power in steps of 0.1dBm."
    ::= { otrMeasuringValuesEntry 3 }

    otrInputPowerHi OBJECT-TYPE
        SYNTAX INTEGER
        ACCESS read-only
        STATUS mandatory
        DESCRIPTION "Input power high warning threshold in steps of 0.1dBm."
    ::= { otrMeasuringValuesEntry 4 }

    otrInputPowerHiHi OBJECT-TYPE
        SYNTAX INTEGER
        ACCESS read-only
        STATUS mandatory
        DESCRIPTION "Input power high alarm threshold in steps of 0.1dBm."
    ::= { otrMeasuringValuesEntry 5 }

-- *****
    otrOutputPowerLoLo OBJECT-TYPE
        SYNTAX INTEGER
        ACCESS read-only
        STATUS mandatory
        DESCRIPTION "Output power low alarm threshold in steps of 0.1dBm."
    ::= { otrMeasuringValuesEntry 6 }

    otrOutputPowerLo OBJECT-TYPE
        SYNTAX INTEGER
        ACCESS read-only
        STATUS mandatory
        DESCRIPTION "Output power low warning threshold in steps of 0.1dBm."
    ::= { otrMeasuringValuesEntry 7 }

    otrOutputPowerValue OBJECT-TYPE
        SYNTAX INTEGER
        ACCESS read-only
        STATUS mandatory
        DESCRIPTION "Output power in steps of 0.1dBm."
    ::= { otrMeasuringValuesEntry 8 }

    otrOutputPowerHi OBJECT-TYPE
        SYNTAX INTEGER
        ACCESS read-only
        STATUS mandatory
        DESCRIPTION "Output power high warning threshold in steps of 0.1dBm."
    ::= { otrMeasuringValuesEntry 9 }

    otrOutputPowerHiHi OBJECT-TYPE
        SYNTAX INTEGER
        ACCESS read-only
        STATUS mandatory
        DESCRIPTION "Output power high alarm threshold in steps of 0.1dBm."
    ::= { otrMeasuringValuesEntry 10 }

-- *****
    otrLaserCurrentRelLoLo OBJECT-TYPE
        SYNTAX INTEGER
        ACCESS read-only
        STATUS mandatory
        DESCRIPTION "Relative laser current low alarm threshold in steps of 0.1%."
    ::= { otrMeasuringValuesEntry 11 }

    otrLaserCurrentRelLo OBJECT-TYPE
        SYNTAX INTEGER
        ACCESS read-only
        STATUS mandatory
        DESCRIPTION "Relative laser current low warning threshold in steps of 0.1%."
    ::= { otrMeasuringValuesEntry 12 }

    otrLaserCurrentRelValue OBJECT-TYPE
        SYNTAX INTEGER
        ACCESS read-only
        STATUS mandatory
        DESCRIPTION "The laser current relative to the current at begin of life in steps of 0.1%."
    ::= { otrMeasuringValuesEntry 13 }

    otrLaserCurrentRelHi OBJECT-TYPE
        SYNTAX INTEGER
        ACCESS read-only
        STATUS mandatory
        DESCRIPTION "Relative laser current high warning threshold in steps of 0.1%."
    ::= { otrMeasuringValuesEntry 14 }

    otrLaserCurrentRelHiHi OBJECT-TYPE
        SYNTAX INTEGER
        ACCESS read-only
        STATUS mandatory
        DESCRIPTION "Relative laser current high alarm threshold in steps of 0.1%."
    ::= { otrMeasuringValuesEntry 15 }

-- *****
    otrPlus24VLoLo OBJECT-TYPE
        SYNTAX INTEGER
        ACCESS read-only
        STATUS mandatory
        DESCRIPTION "The +24V supply voltage low alarm threshold in steps of 0.1V."
    ::= { otrMeasuringValuesEntry 16 }

    otrPlus24VLo OBJECT-TYPE
        SYNTAX INTEGER
        ACCESS read-only
        STATUS mandatory
        DESCRIPTION "The +24V supply voltage low warning threshold in steps of 0.1V."
    ::= { otrMeasuringValuesEntry 17 }

    otrPlus24VValue OBJECT-TYPE
        SYNTAX INTEGER
        ACCESS read-only
        STATUS mandatory
        DESCRIPTION "The +24V supply voltage in steps of 0.1V."
    ::= { otrMeasuringValuesEntry 18 }

    otrPlus24VHi OBJECT-TYPE
        SYNTAX INTEGER
        ACCESS read-only
        STATUS mandatory
        DESCRIPTION "The +24V supply voltage high warning threshold in steps of 0.1V."
    ::= { otrMeasuringValuesEntry 19 }

    otrPlus24VHiHi OBJECT-TYPE
        SYNTAX INTEGER
        ACCESS read-only
        STATUS mandatory
        DESCRIPTION "The +24V supply voltage high alarm threshold in steps of 0.1V."
    ::= { otrMeasuringValuesEntry 20 }

-- *****
    otrTemperatureLoLo OBJECT-TYPE
        SYNTAX INTEGER
        ACCESS read-only
        STATUS mandatory
        DESCRIPTION "The module temperature low alarm threshold in steps of 0.1 celsius degrees."
    ::= { otrMeasuringValuesEntry 21 }

    otrTemperatureLo OBJECT-TYPE
        SYNTAX INTEGER
        ACCESS read-only
        STATUS mandatory
        DESCRIPTION "The module temperature low warning threshold in steps of 0.1 celsius degrees."
    ::= { otrMeasuringValuesEntry 22 }

    otrTemperatureValue OBJECT-TYPE
        SYNTAX INTEGER
        ACCESS read-only
        STATUS mandatory
        DESCRIPTION "The module temperature in steps of 0.1 celsius degrees."
    ::= { otrMeasuringValuesEntry 23 }

    otrTemperatureHi OBJECT-TYPE
        SYNTAX INTEGER
        ACCESS read-only
        STATUS mandatory
        DESCRIPTION "The module temperature high warning threshold in steps of 0.1 celsius degrees."
    ::= { otrMeasuringValuesEntry 24 }

    otrTemperatureHiHi OBJECT-TYPE
        SYNTAX INTEGER
        ACCESS read-only
        STATUS mandatory
        DESCRIPTION "The module temperature high alarm threshold in steps of 0.1 celsius degrees."
    ::= { otrMeasuringValuesEntry 25 }


--*****************************************************************************************
--  otrStates group

-- Note: For every control OId there must be a correspondant alarm OId!

    otrStatesTable OBJECT-TYPE
        SYNTAX SEQUENCE OF OtrStatesEntry
        ACCESS not-accessible
        STATUS mandatory
        DESCRIPTION ""
    ::= { otrStates 1 }

-- table of states entry(ro/rw)

    otrStatesEntry OBJECT-TYPE
        SYNTAX OtrStatesEntry
        ACCESS not-accessible
        STATUS mandatory
        DESCRIPTION "Alarms for a module."
        INDEX { otrNESlot }
    ::= { otrStatesTable 1 }

-- the structure of the entry

    OtrStatesEntry ::= SEQUENCE
    {
        otrStatesInputLow            PerceivedSeverityValue,
        otrStatesInputHigh           PerceivedSeverityValue,
        otrStatesOutputLow           PerceivedSeverityValue,
        otrStatesOutputHigh          PerceivedSeverityValue,
        otrStatesLaserAging          PerceivedSeverityValue,
        otrStatesPlus24VLow          PerceivedSeverityValue,
        otrStatesPlus24VHigh         PerceivedSeverityValue,
        otrStatesTemperatureLow      PerceivedSeverityValue,
        otrStatesTemperatureHigh     PerceivedSeverityValue,
        otrStatesLidOpen             PerceivedSeverityValue,
        otrStatesSwitchedToRedundant PerceivedSeverityValue,
        otrStatesTxPilotFailure      PerceivedSeverityValue,
        otrStatesTxShutdown          PerceivedSeverityValue,
        otrStatesBootloader          PerceivedSeverityValue,
        otrStatesDefective           PerceivedSeverityValue
    }

    otrStatesInputLow OBJECT-TYPE
        SYNTAX PerceivedSeverityValue
        ACCESS read-only
        STATUS mandatory
        DESCRIPTION "Optical input power low"
    ::= { otrStatesEntry 1 }

    otrStatesInputHigh OBJECT-TYPE
        SYNTAX PerceivedSeverityValue
        ACCESS read-only
        STATUS mandatory
        DESCRIPTION "Optical input power high"
    ::= { otrStatesEntry 2 }

    otrStatesOutputLow OBJECT-TYPE
        SYNTAX PerceivedSeverityValue
        ACCESS read-only
        STATUS mandatory
        DESCRIPTION "Optical output power low"
    ::= { otrStatesEntry 3 }

    otrStatesOutputHigh OBJECT-TYPE
        SYNTAX PerceivedSeverityValue
        ACCESS read-only
        STATUS mandatory
        DESCRIPTION "Optical output power high"
    ::= { otrStatesEntry 4 }

    otrStatesLaserAging OBJECT-TYPE
        SYNTAX PerceivedSeverityValue
        ACCESS read-only
        STATUS mandatory
        DESCRIPTION "The laser is aging"
    ::= { otrStatesEntry 5 }

    otrStatesPlus24VLow OBJECT-TYPE
        SYNTAX PerceivedSeverityValue
        ACCESS read-only
        STATUS mandatory
        DESCRIPTION "24 Volt supply low"
    ::= { otrStatesEntry 6 }

    otrStatesPlus24VHigh OBJECT-TYPE
        SYNTAX PerceivedSeverityValue
        ACCESS read-only
        STATUS mandatory
        DESCRIPTION "24 Volt supply high"
    ::= { otrStatesEntry 7 }

    otrStatesTemperatureLow OBJECT-TYPE
        SYNTAX PerceivedSeverityValue
        ACCESS read-only
        STATUS mandatory
        DESCRIPTION "Device internal temperature low"
    ::= { otrStatesEntry 8 }

    otrStatesTemperatureHigh OBJECT-TYPE
        SYNTAX PerceivedSeverityValue
        ACCESS read-only
        STATUS mandatory
        DESCRIPTION "Device internal temperature high"
    ::= { otrStatesEntry 9 }

    otrStatesLidOpen OBJECT-TYPE
        SYNTAX PerceivedSeverityValue
        ACCESS read-only
        STATUS mandatory
        DESCRIPTION "The lid of the BK rack is open"
    ::= { otrStatesEntry 10 }

    otrStatesSwitchedToRedundant OBJECT-TYPE
        SYNTAX PerceivedSeverityValue
        ACCESS read-only
        STATUS mandatory
        DESCRIPTION "The device has executed a redundancy switch"
    ::= { otrStatesEntry 11 }

    otrStatesTxPilotFailure OBJECT-TYPE
        SYNTAX PerceivedSeverityValue
        ACCESS read-only
        STATUS mandatory
        DESCRIPTION "Pilot failure"
    ::= { otrStatesEntry 12 }

    otrStatesTxShutdown OBJECT-TYPE
        SYNTAX PerceivedSeverityValue
        ACCESS read-only
        STATUS mandatory
        DESCRIPTION "Transmitter shutdown by -6dB"
    ::= { otrStatesEntry 13 }

    otrStatesBootloader OBJECT-TYPE
        SYNTAX PerceivedSeverityValue
        ACCESS read-only
        STATUS mandatory
        DESCRIPTION 
            "The device is running in bootloader mode 
             without a legal application software." 
    ::= { otrStatesEntry 14 }

    otrStatesDefective OBJECT-TYPE
        SYNTAX PerceivedSeverityValue
        ACCESS read-only
        STATUS mandatory
        DESCRIPTION
            "The NEC has lost the connection to the device. 
             Reason may be a removed or defective device.
             Note that this state is set by the NEC and not 
             by the device" 
    ::= { otrStatesEntry 15 }

--*****************************************************************************************
--  otrControl group

  otrControlTable OBJECT-TYPE
    SYNTAX SEQUENCE OF OtrControlEntry
    ACCESS not-accessible
    STATUS mandatory
    DESCRIPTION ""
  ::= { otrControl 1 }

-- table of control entry(ro/rw)

  otrControlEntry OBJECT-TYPE
    SYNTAX OtrControlEntry
    ACCESS not-accessible
    STATUS mandatory
    DESCRIPTION "Alarms for a module."
    INDEX { otrNESlot }
  ::= { otrControlTable 1 }

-- the structure of the entry

    OtrControlEntry ::= SEQUENCE
    {
        otrControlReset               TruthValue,
        otrControlModuleLedBlink      TruthValue,
        otrControlLaserShutdown       TruthValue
    }

    otrControlReset OBJECT-TYPE
      SYNTAX TruthValue
      ACCESS read-write
      STATUS mandatory
      DESCRIPTION "Reset the module."
    ::= { otrControlEntry 1 }

    otrControlModuleLedBlink OBJECT-TYPE
        SYNTAX TruthValue
        ACCESS read-write
        STATUS mandatory
        DESCRIPTION   "Writing this variable to true(1) lets the device's 
        modul LED blink green for 10 seconds. 
        Writing this variable to false(2) stotr blinking at once.
        This variable always returns false(2) on read requests"
    ::= { otrControlEntry 2 }

    otrControlLaserShutdown OBJECT-TYPE
        SYNTAX TruthValue
        ACCESS read-write
        STATUS mandatory
        DESCRIPTION "Allows to shutdown the transmitter (Laser output power minus 6dB)."
    ::= { otrControlEntry 3 }


--*****************************************************************************************
-- otrConfiguration group

    otrConfigurationTable OBJECT-TYPE
        SYNTAX SEQUENCE OF OtrConfigurationEntry
        ACCESS not-accessible
        STATUS mandatory
        DESCRIPTION ""
    ::= { otrConfiguration 1 }

-- table of configuration entry(ro/rw)

    otrConfigurationEntry OBJECT-TYPE
        SYNTAX OtrConfigurationEntry
        ACCESS not-accessible
        STATUS mandatory
        DESCRIPTION ""
        INDEX { otrNESlot  }
    ::= { otrConfigurationTable 1 }

-- the structure of the entry

    OtrConfigurationEntry ::= SEQUENCE
    {
        -- Common
        otrConfigNESlotWrite             NESlotWriteValue,
        otrConfigLedActivity             LedActivityValue,
        -- Receiver
        otrConfigInputPwrLimitLoLo       INTEGER,
        otrConfigInputPwrLimitLo         INTEGER,
        otrConfigInputPwrLimitHi         INTEGER,
        otrConfigInputPwrLimitHiHi       INTEGER,
        otrConfigRfOutDcSettingsEnable   TruthValue,
        otrConfigAuxRfOutputMode         AuxRfOutputModeValue,        
        -- Transmitter
        otrConfigAuxRfInputMode          AuxRfInputModeValue,
        otrConfigOmi                     INTEGER,
        otrConfigSendPilotSignal         TruthValue,
        otrConfigLineCodeEnable          TruthValue,
        otrConfigLineCodeNumber          LineCodeNumberValue,
        otrConfigLineCodeNomRedFlag      LineCodeNomRedFlagValue,
        -- Receiver
        otrConfigOutputVoltageOffset     INTEGER
    }

-- Common part
    
    otrConfigNESlotWrite OBJECT-TYPE
        SYNTAX NESlotWriteValue
        ACCESS read-write
        STATUS optional
        DESCRIPTION "By writing this variable a slot can be assigned
            for devices that dont support hardware slot detection.
            Reading '-1' means that the slot position is NOT writable."
    ::= { otrConfigurationEntry 1 }

    otrConfigLedActivity OBJECT-TYPE
        SYNTAX LedActivityValue
        ACCESS read-write
        STATUS mandatory
        DESCRIPTION 
            "Set the activity mode of the device LED's.   
             Can be used to save some power in fibernodes."
    ::= { otrConfigurationEntry 2 }

-- Receiver part
    
    otrConfigInputPwrLimitLoLo OBJECT-TYPE
        SYNTAX  INTEGER
        ACCESS  read-write
        STATUS  mandatory
        DESCRIPTION
            "The optical input power low alarm limit in 0.1 dBm units"
    ::={ otrConfigurationEntry 3 }

    otrConfigInputPwrLimitLo OBJECT-TYPE
        SYNTAX  INTEGER
        ACCESS  read-write
        STATUS  mandatory
        DESCRIPTION
            "The optical input power low warning limit in 0.1 dBm units"
    ::={ otrConfigurationEntry 4 }

    otrConfigInputPwrLimitHi OBJECT-TYPE
        SYNTAX  INTEGER
        ACCESS  read-write
        STATUS  mandatory
        DESCRIPTION
            "The optical input power high warning limit in 0.1 dBm units"
    ::={ otrConfigurationEntry 5 }

    otrConfigInputPwrLimitHiHi OBJECT-TYPE
        SYNTAX  INTEGER
        ACCESS  read-write
        STATUS  mandatory
        DESCRIPTION
            "The optical input power high alarm limit in 0.1 dBm units"
    ::={ otrConfigurationEntry 6 }

    otrConfigRfOutDcSettingsEnable OBJECT-TYPE
        SYNTAX  TruthValue
        ACCESS  read-write
        STATUS  mandatory
        DESCRIPTION
            "The OTR can be DC remote controlled by the rf-module that
             follows the optical receiver's main rf-output for redundancy 
             purposes.
             Allows to enable or disable this DC remote control feature."
    ::={ otrConfigurationEntry 7 }

    otrConfigAuxRfOutputMode OBJECT-TYPE
        SYNTAX  AuxRfOutputModeValue
        ACCESS  read-write
        STATUS  mandatory
        DESCRIPTION
            "The mode of the receivers auxiliary rf output.
             Note that dcRemoteControlled(1) is a possible value 
             only if RfOutDcSettings is enabled"
    ::={ otrConfigurationEntry 8 }

-- Transmitter part

    otrConfigAuxRfInputMode OBJECT-TYPE
        SYNTAX  AuxRfInputModeValue
        ACCESS  read-write
        STATUS  mandatory
        DESCRIPTION "The mode of the transmitters auxiliary rf input"
    ::={ otrConfigurationEntry 9 }

    otrConfigOmi OBJECT-TYPE
        SYNTAX INTEGER
        ACCESS read-write
        STATUS mandatory
        DESCRIPTION "The optical modulation index in 0.1 percent units."
    ::= { otrConfigurationEntry 10 }

    otrConfigSendPilotSignal OBJECT-TYPE
        SYNTAX TruthValue
        ACCESS read-write
        STATUS mandatory
        DESCRIPTION "Enable/disable transmitter's sending of pilot signal."
    ::= { otrConfigurationEntry 11 }

    otrConfigLineCodeEnable OBJECT-TYPE
        SYNTAX TruthValue
        ACCESS read-write
        STATUS mandatory
        DESCRIPTION "Enable/disable transmitter's sending of line code signals."
    ::= { otrConfigurationEntry 12 }

    otrConfigLineCodeNumber OBJECT-TYPE
        SYNTAX LineCodeNumberValue
        ACCESS read-write
        STATUS mandatory
        DESCRIPTION 
            "The line code number that the transmitter shall send.
             This line code number can be used on the remote side 
             optical receiver to identify the connected transmitter."
    ::= { otrConfigurationEntry 13 }

    otrConfigLineCodeNomRedFlag OBJECT-TYPE
        SYNTAX LineCodeNomRedFlagValue
        ACCESS read-write
        STATUS mandatory
        DESCRIPTION 
            "The line code nominal/redundant flag that the transmitter shall send.
             This flag informs the remote optical receiver (orx2) if this OTR device 
             acts as nominal or as redundant device."
    ::= { otrConfigurationEntry 14 }

    otrConfigOutputVoltageOffset OBJECT-TYPE
        SYNTAX  INTEGER
        ACCESS  read-write
        STATUS  mandatory
        DESCRIPTION
            "The offset from nominal output level voltage in 0.1 dB units"
    ::={ otrConfigurationEntry 15 }



--*****************************************************************************************
-- Display group

    otrDisplayTable OBJECT-TYPE
        SYNTAX SEQUENCE OF OtrDisplayEntry
        ACCESS not-accessible
        STATUS mandatory
        DESCRIPTION ""
    ::= { otrDisplay 1 }

-- table of configuration entry(ro/rw)

    otrDisplayEntry OBJECT-TYPE
        SYNTAX OtrDisplayEntry
        ACCESS not-accessible
        STATUS mandatory
        DESCRIPTION ""
        INDEX { otrNESlot  }
    ::= { otrDisplayTable 1 }

-- the structure of the entry

    OtrDisplayEntry ::= SEQUENCE
    {
        otrDisplayRxActive           TruthValue,
        otrDisplayRxAuxOutputActive  TruthValue,
        otrDisplayTxAuxInputActive   TruthValue
    }

    otrDisplayRxActive OBJECT-TYPE
        SYNTAX TruthValue
        ACCESS read-only
        STATUS mandatory
        DESCRIPTION 
            "The activity state of the optical receiver. 
             If not active the complete receiver sleeps with low power consumption."
      ::= { otrDisplayEntry 1 }

    otrDisplayRxAuxOutputActive OBJECT-TYPE
        SYNTAX TruthValue
        ACCESS read-only
        STATUS mandatory
        DESCRIPTION "The auxiliary rf output activity state of the optical receiver."
      ::= { otrDisplayEntry 2 }

    otrDisplayTxAuxInputActive OBJECT-TYPE
        SYNTAX TruthValue
        ACCESS read-only
        STATUS mandatory
        DESCRIPTION "The auxiliary rf input activity state of the optical transmitter."
      ::= { otrDisplayEntry 3 }



--*****************************************************************************************
END
