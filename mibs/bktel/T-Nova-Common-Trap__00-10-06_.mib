--***********************************************************
-- 17.11.03, Heldmann, BKtel, Removed german language descriptions
--***********************************************************

-- **************************************************************
-- T-NOVA-COMMON-TRAP-MIB
--
-- Revision Notes:
-- 06.10.00  Klaus Biedenbach, T-Nova, E531i
-- 				erster Entwurf
-- 25.10.00  Klaus Biedenbach, T-Nova, E531i
--				minimale redaktinelle Änderungen
-- **************************************************************

T-NOVA-COMMON-TRAP-MIB DEFINITIONS ::= BEGIN

IMPORTS
	commonTrapControl 	FROM T-NOVA-ROOT-MIB;


trapSequenceNumber OBJECT-TYPE
	SYNTAX INTEGER
	ACCESS read-only
	STATUS mandatory
	DESCRIPTION
		"Every trap contains a sequence number. 
		The variable trapSequenceNumber contains the sequence number 
		of the next trap to be sent. After creating a new trap, 
		trapSequenceNumber will be incremented. 
		By reading the trapSequenceNumber a manager can find out 
		the sequence number of the most recent trap being sent. 
		A trap must have been lost, if the agents 
		(trapSequenceNumber - 1) differs from the sequence number of 
		the latest received trap."
	::= { commonTrapControl 1 }

END
