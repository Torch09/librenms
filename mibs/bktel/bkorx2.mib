--- ****************************************************************************
-- *
-- * Description:   Implements definitions for the Orx2-modul
-- *                (Optical Dual Receiver (BOR265) design release V01)
-- *
-- * Copyright 2003 by BKtel communications GmbH
-- *
-- *
-- *     V.0.1 18.06.03  M. Heldmann    first draft
-- *     V.0.2 23.07.03  M. Heldmann    added descriptions for the states
-- *     V.0.3 28.10.03  M. Heldmann    expanded 'orx2ConfigRedundancySetting' and
-- *                                             'orx2ConfigLineCodeUsage' parameters
-- *     V.0.4 07.01.04  M. Heldmann    added 'orx2ConfigPilotRegulationMode_Chn1' .. 'orx2ConfigInputAttenDigits_Chn2'
-- *     V.0.5 16.08.06  M. Heldmann    changed 'RfOutputLevelValue' definition
-- *     V.0.6 04.10.06  M. Heldmann    NESlotWriteValue expanded due to new 2G6 platform needs
-- *     V.0.7 29.05.08  M. Heldmann    renamed threshold parameters in xxxxMeasuringValuesTable
-- *     V.0.8 11.07.13  M. Heldmann    adjusted syntax of "CommonEntry" to remove MIB compiler warnings
-- *     V.0.9 05.09.14  M. Heldmann    changed CommonModuleWidth and ConfigNESlotWrite STATUS to optional
-- ****************************************************************************

BKTEL-HFC862-ORX2-V01-MIB DEFINITIONS ::= BEGIN

    IMPORTS
        experimental, enterprises, TimeTicks, IpAddress, Counter
                 FROM RFC1155-SMI
    OBJECT-TYPE
                 FROM RFC-1212
        TRAP-TYPE
                 FROM RFC-1215
        modules, DisplayString, TruthValue, PerceivedSeverityValue, NESlotValue, ModuleWidthValue
                 FROM   BKTEL-HFC862-BASE-MIB
    ;

    orx2                 OBJECT IDENTIFIER ::= { modules 108 }
    orx2Common           OBJECT IDENTIFIER ::= { orx2 1 }
    orx2States           OBJECT IDENTIFIER ::= { orx2 2 }
    orx2Configuration    OBJECT IDENTIFIER ::= { orx2 3 }
    orx2Control          OBJECT IDENTIFIER ::= { orx2 4 }
    orx2MeasuringValues  OBJECT IDENTIFIER ::= { orx2 5 }
    orx2Display          OBJECT IDENTIFIER ::= { orx2 6 }


--
-- Type definitions
--

        NESlotWriteValue ::= INTEGER (-1..99)

        OutputModeValue ::= INTEGER
            {
            separateOutputs(1),
            commonOutput(2)
            }

        LinecodeModeValue ::= INTEGER
            {
            fullEnableLinecodes(1),
            fullDisableLinecodes(2),
            displayLinecodesOnly(3),
            displayLinecodesAndEnableAlarms(4)
            }

        RedundancySettingValue ::= INTEGER
            {
            noRedundancy(1),
            deviceRedundancy(2),
            channelRedundancy(3)
            }

        RedundancyModeValue ::= INTEGER
            {
            nominalDevice(1),
            redundantDevice(2)
            }

        IngressModeValue ::= INTEGER
            {
            noAttenuator(1),
            attenuator_6dB(2),
            attenuator_60dB(3)
            }

        RfOutputLevelValue ::= INTEGER
            {
            level_Low(1),
            level_High(2)
            }

        LineCodeNumberValue ::= INTEGER (0..999)

        LineCodeRcvdNomRedFlagValue ::= INTEGER
            {
            rcvdNominalFlag(1),
            rcvdRedundantFlag(2),
            rcvdUnknown(3)
            }

        PilotRegulationModeValue ::= INTEGER
            {
            regulationDisabled(1),
            regulationEnabled(2)
            }

        InputAttenDigitsValue ::= INTEGER (0..4095)


-- MibCompiler defs --
-- $idx$: _Chn
-- MibCompiler defs --


--*****************************************************************************************
-- ORX2 (Optical Dual Receiver (BOR265) design release V01)

--*****************************************************************************************
-- orx2Common group

    orx2CommonNumberOfModules OBJECT-TYPE
        SYNTAX  INTEGER(0..50)
        ACCESS  read-only
        STATUS  mandatory
        DESCRIPTION "Number of modules in table."
  ::= { orx2Common 1 }

    orx2CommonTable OBJECT-TYPE
        SYNTAX SEQUENCE OF Orx2CommonEntry
        ACCESS not-accessible
        STATUS mandatory
        DESCRIPTION "The table contains all modules of the ORX2-type in the NE"
  ::= { orx2Common 2 }

-- table of states entry(ro/rw)

    orx2CommonEntry OBJECT-TYPE
        SYNTAX Orx2CommonEntry
        ACCESS not-accessible
        STATUS mandatory
        DESCRIPTION "Common-Values for a module."
        INDEX { orx2NESlot }
  ::= { orx2CommonTable 1 }

-- the structure of the entry

    Orx2CommonEntry ::= SEQUENCE
    {
        orx2NESlot                      NESlotValue,
        orx2CommonType                  DisplayString,
        orx2CommonDescr                 DisplayString,
        orx2CommonFirmwareId            DisplayString,
        orx2CommonModuleWidth           ModuleWidthValue
    }

    orx2NESlot OBJECT-TYPE
        SYNTAX  NESlotValue
        ACCESS  read-only
        STATUS  mandatory
        DESCRIPTION
        "The slot number of the chassis for which this
        entry contains management information."
    ::= { orx2CommonEntry 1 }

    orx2CommonType OBJECT-TYPE
        SYNTAX  DisplayString  (SIZE(0..32))
        ACCESS  read-only
        STATUS  mandatory
        DESCRIPTION
        "The type of physical module. modSlotEmpty indicates
         an empty slot.  A Value of modSlotUnknown indicates
         that the type of module is unknown."
    ::= { orx2CommonEntry 2 }

    orx2CommonDescr OBJECT-TYPE
        SYNTAX  DisplayString
        ACCESS  read-write
        STATUS  mandatory
        DESCRIPTION
        "A textual description of the module.
        If not available, this Value should be
        set to a zero length string."
    ::= { orx2CommonEntry 3 }

    orx2CommonFirmwareId OBJECT-TYPE
        SYNTAX DisplayString (SIZE(0..32))
        ACCESS read-only
        STATUS mandatory
        DESCRIPTION "The firmware Id of the module."
    ::= { orx2CommonEntry 4 }

    orx2CommonModuleWidth OBJECT-TYPE
        SYNTAX ModuleWidthValue
        ACCESS read-only
        STATUS optional
        DESCRIPTION "The width of the module in multiples of slots (1, 2, ...)"
    ::= { orx2CommonEntry 5 }

--*****************************************************************************************
-- orx2MeasuringValues group

-- table of measuring Values

    orx2MeasuringValuesTable OBJECT-TYPE
        SYNTAX SEQUENCE OF Orx2MeasuringValuesEntry
        ACCESS not-accessible
        STATUS mandatory
        DESCRIPTION ""
   ::= { orx2MeasuringValues 1 }

-- table of measuring Values entry

    orx2MeasuringValuesEntry OBJECT-TYPE
        SYNTAX Orx2MeasuringValuesEntry
        ACCESS not-accessible
        STATUS mandatory
        DESCRIPTION "Common-Values for a module."
        INDEX { orx2NESlot }
  ::= { orx2MeasuringValuesTable 1 }

--  the structure of the entry

    Orx2MeasuringValuesEntry ::= SEQUENCE
    {
        orx2InputPowerLoLo_Chn1        INTEGER,
        orx2InputPowerLo_Chn1          INTEGER,
        orx2InputPowerValue_Chn1       INTEGER,
        orx2InputPowerHi_Chn1          INTEGER,
        orx2InputPowerHiHi_Chn1        INTEGER,

        orx2InputPowerLoLo_Chn2        INTEGER,
        orx2InputPowerLo_Chn2          INTEGER,
        orx2InputPowerValue_Chn2       INTEGER,
        orx2InputPowerHi_Chn2          INTEGER,
        orx2InputPowerHiHi_Chn2        INTEGER,

        orx2TemperatureLoLo            INTEGER,
        orx2TemperatureLo              INTEGER,
        orx2TemperatureValue           INTEGER,
        orx2TemperatureHi              INTEGER,
        orx2TemperatureHiHi            INTEGER
    }

-- *****
    orx2InputPowerLoLo_Chn1 OBJECT-TYPE
        SYNTAX INTEGER
        ACCESS read-only
        STATUS mandatory
        DESCRIPTION "Input power low alarm threshold in steps of 0.1dBm (Channel no.1)."
    ::= { orx2MeasuringValuesEntry 1 }

    orx2InputPowerLo_Chn1 OBJECT-TYPE
        SYNTAX INTEGER
        ACCESS read-only
        STATUS mandatory
        DESCRIPTION "Input power low warning threshold in steps of 0.1dBm (Channel no.1)."
    ::= { orx2MeasuringValuesEntry 2 }

    orx2InputPowerValue_Chn1 OBJECT-TYPE
        SYNTAX INTEGER
        ACCESS read-only
        STATUS mandatory
        DESCRIPTION "Input power in steps of 0.1dBm (Channel no.1)."
    ::= { orx2MeasuringValuesEntry 3 }

    orx2InputPowerHi_Chn1 OBJECT-TYPE
        SYNTAX INTEGER
        ACCESS read-only
        STATUS mandatory
        DESCRIPTION "Input power high warning threshold in steps of 0.1dBm (Channel no.1)."
    ::= { orx2MeasuringValuesEntry 4 }

    orx2InputPowerHiHi_Chn1 OBJECT-TYPE
        SYNTAX INTEGER
        ACCESS read-only
        STATUS mandatory
        DESCRIPTION "Input power high alarm threshold in steps of 0.1dBm (Channel no.1)."
    ::= { orx2MeasuringValuesEntry 5 }

-- *****
    orx2InputPowerLoLo_Chn2 OBJECT-TYPE
        SYNTAX INTEGER
        ACCESS read-only
        STATUS mandatory
        DESCRIPTION "Input power low alarm threshold in steps of 0.1dBm (Channel no.2)."
    ::= { orx2MeasuringValuesEntry 6 }

    orx2InputPowerLo_Chn2 OBJECT-TYPE
        SYNTAX INTEGER
        ACCESS read-only
        STATUS mandatory
        DESCRIPTION "Input power low warning threshold in steps of 0.1dBm (Channel no.2)."
    ::= { orx2MeasuringValuesEntry 7 }

    orx2InputPowerValue_Chn2 OBJECT-TYPE
        SYNTAX INTEGER
        ACCESS read-only
        STATUS mandatory
        DESCRIPTION "Input power in steps of 0.1dBm (Channel no.2)."
    ::= { orx2MeasuringValuesEntry 8 }

    orx2InputPowerHi_Chn2 OBJECT-TYPE
        SYNTAX INTEGER
        ACCESS read-only
        STATUS mandatory
        DESCRIPTION "Input power high warning threshold in steps of 0.1dBm (Channel no.2)."
    ::= { orx2MeasuringValuesEntry 9 }

    orx2InputPowerHiHi_Chn2 OBJECT-TYPE
        SYNTAX INTEGER
        ACCESS read-only
        STATUS mandatory
        DESCRIPTION "Input power high alarm threshold in steps of 0.1dBm (Channel no.2)."
    ::= { orx2MeasuringValuesEntry 10 }

-- *****
    orx2TemperatureLoLo OBJECT-TYPE
        SYNTAX INTEGER
        ACCESS read-only
        STATUS mandatory
        DESCRIPTION "The module temperature low alarm threshold in steps of 0.1 celsius degrees."
    ::= { orx2MeasuringValuesEntry 11 }

    orx2TemperatureLo OBJECT-TYPE
        SYNTAX INTEGER
        ACCESS read-only
        STATUS mandatory
        DESCRIPTION "The module temperature low warning threshold in steps of 0.1 celsius degrees."
    ::= { orx2MeasuringValuesEntry 12 }

    orx2TemperatureValue OBJECT-TYPE
        SYNTAX INTEGER
        ACCESS read-only
        STATUS mandatory
        DESCRIPTION "The module temperature in steps of 0.1 celsius degrees."
    ::= { orx2MeasuringValuesEntry 13 }

    orx2TemperatureHi OBJECT-TYPE
        SYNTAX INTEGER
        ACCESS read-only
        STATUS mandatory
        DESCRIPTION "The module temperature high warning threshold in steps of 0.1 celsius degrees."
    ::= { orx2MeasuringValuesEntry 14 }

    orx2TemperatureHiHi OBJECT-TYPE
        SYNTAX INTEGER
        ACCESS read-only
        STATUS mandatory
        DESCRIPTION "The module temperature high alarm threshold in steps of 0.1 celsius degrees."
    ::= { orx2MeasuringValuesEntry 15 }


--*****************************************************************************************
--  orx2States group

-- Note: For every control OId there must be a correspondant alarm OId!

    orx2StatesTable OBJECT-TYPE
        SYNTAX SEQUENCE OF Orx2StatesEntry
        ACCESS not-accessible
        STATUS mandatory
        DESCRIPTION ""
    ::= { orx2States 1 }

-- table of states entry(ro/rw)

    orx2StatesEntry OBJECT-TYPE
        SYNTAX Orx2StatesEntry
        ACCESS not-accessible
        STATUS mandatory
        DESCRIPTION "Alarms for a module."
        INDEX { orx2NESlot }
    ::= { orx2StatesTable 1 }

-- the structure of the entry

    Orx2StatesEntry ::= SEQUENCE
    {
        orx2StatesInputLow_Chn1           PerceivedSeverityValue,
        orx2StatesInputHigh_Chn1          PerceivedSeverityValue,
        orx2StatesInputLow_Chn2           PerceivedSeverityValue,
        orx2StatesInputHigh_Chn2          PerceivedSeverityValue,
        orx2StatesTemperatureLow          PerceivedSeverityValue,
        orx2StatesTemperatureHigh         PerceivedSeverityValue,
        orx2StatesPilotSignal_Chn1        PerceivedSeverityValue,
        orx2StatesPilotSignal_Chn2        PerceivedSeverityValue,
        orx2StatesRegulatorLimit_Chn1     PerceivedSeverityValue,
        orx2StatesRegulatorLimit_Chn2     PerceivedSeverityValue,
        orx2StatesLineCodeState_Chn1      PerceivedSeverityValue,
        orx2StatesLineCodeState_Chn2      PerceivedSeverityValue,
        orx2StatesLineCodeNumber_Chn1     PerceivedSeverityValue,
        orx2StatesLineCodeNumber_Chn2     PerceivedSeverityValue,
        orx2StatesLineCodeNomRedMismatch  PerceivedSeverityValue,
        orx2StatesSwitchedToRedundant     PerceivedSeverityValue,
        orx2StatesLineCodeDisabled        PerceivedSeverityValue,
        orx2StatesBootloader              PerceivedSeverityValue,
        orx2StatesDefective               PerceivedSeverityValue
    }

    orx2StatesInputLow_Chn1 OBJECT-TYPE
        SYNTAX PerceivedSeverityValue
        ACCESS read-only
        STATUS mandatory
        DESCRIPTION "Optical input power (input channel 1) low"
    ::= { orx2StatesEntry 1 }

    orx2StatesInputHigh_Chn1 OBJECT-TYPE
        SYNTAX PerceivedSeverityValue
        ACCESS read-only
        STATUS mandatory
        DESCRIPTION "Optical input power (input channel 1) high"
    ::= { orx2StatesEntry 2 }

    orx2StatesInputLow_Chn2 OBJECT-TYPE
        SYNTAX PerceivedSeverityValue
        ACCESS read-only
        STATUS mandatory
        DESCRIPTION "Optical input power (input channel 2) low"
    ::= { orx2StatesEntry 3 }

    orx2StatesInputHigh_Chn2 OBJECT-TYPE
        SYNTAX PerceivedSeverityValue
        ACCESS read-only
        STATUS mandatory
        DESCRIPTION "Optical input power (input channel 2) high"
    ::= { orx2StatesEntry 4 }

    orx2StatesTemperatureLow OBJECT-TYPE
        SYNTAX PerceivedSeverityValue
        ACCESS read-only
        STATUS mandatory
        DESCRIPTION "Device internal temperature low"
    ::= { orx2StatesEntry 5 }

    orx2StatesTemperatureHigh OBJECT-TYPE
        SYNTAX PerceivedSeverityValue
        ACCESS read-only
        STATUS mandatory
        DESCRIPTION "Device internal temperature high"
    ::= { orx2StatesEntry 6 }

    orx2StatesPilotSignal_Chn1 OBJECT-TYPE
        SYNTAX PerceivedSeverityValue
        ACCESS read-only
        STATUS mandatory
        DESCRIPTION "Pilot signal failure (input channel 1)"
    ::= { orx2StatesEntry 7 }

    orx2StatesPilotSignal_Chn2 OBJECT-TYPE
        SYNTAX PerceivedSeverityValue
        ACCESS read-only
        STATUS mandatory
        DESCRIPTION "Pilot signal failure (input channel 2)"
    ::= { orx2StatesEntry 8 }

    orx2StatesRegulatorLimit_Chn1 OBJECT-TYPE
        SYNTAX PerceivedSeverityValue
        ACCESS read-only
        STATUS mandatory
        DESCRIPTION "Optical input regulator limit reached (input channel 1)"
    ::= { orx2StatesEntry 9 }

    orx2StatesRegulatorLimit_Chn2 OBJECT-TYPE
        SYNTAX PerceivedSeverityValue
        ACCESS read-only
        STATUS mandatory
        DESCRIPTION "Optical input regulator limit reached (input channel 2)"
    ::= { orx2StatesEntry 10 }

    orx2StatesLineCodeState_Chn1 OBJECT-TYPE
        SYNTAX PerceivedSeverityValue
        ACCESS read-only
        STATUS mandatory
        DESCRIPTION "No valid line code received (input channel 1)"
    ::= { orx2StatesEntry 11 }

    orx2StatesLineCodeState_Chn2 OBJECT-TYPE
        SYNTAX PerceivedSeverityValue
        ACCESS read-only
        STATUS mandatory
        DESCRIPTION "No valid line code received (input channel 2)"
    ::= { orx2StatesEntry 12 }

    orx2StatesLineCodeNumber_Chn1 OBJECT-TYPE
        SYNTAX PerceivedSeverityValue
        ACCESS read-only
        STATUS mandatory
        DESCRIPTION "Received line code number is not equal to the expected (input channel 1)"
    ::= { orx2StatesEntry 13 }

    orx2StatesLineCodeNumber_Chn2 OBJECT-TYPE
        SYNTAX PerceivedSeverityValue
        ACCESS read-only
        STATUS mandatory
        DESCRIPTION "Received line code number is not equal to the expected (input channel 2)"
    ::= { orx2StatesEntry 14 }

    orx2StatesLineCodeNomRedMismatch OBJECT-TYPE
        SYNTAX PerceivedSeverityValue
        ACCESS read-only
        STATUS mandatory
        DESCRIPTION "Received nominal/redundant line code flag is not equal for both receive channels"
    ::= { orx2StatesEntry 15 }

    orx2StatesSwitchedToRedundant OBJECT-TYPE
        SYNTAX PerceivedSeverityValue
        ACCESS read-only
        STATUS mandatory
        DESCRIPTION 
            "The device has executed a redundancy switch"
            -- This occurs either 
            --   - if the device was running as the nominal device and has changed to inactice state now
            -- or 
            --   - if the device was running as the redundant device and has changed to actice state now
    ::= { orx2StatesEntry 16 }

    orx2StatesLineCodeDisabled OBJECT-TYPE
        SYNTAX PerceivedSeverityValue
        ACCESS read-only
        STATUS mandatory
        DESCRIPTION "The line codes handling is disabled"
    ::= { orx2StatesEntry 17 }

    orx2StatesBootloader OBJECT-TYPE
        SYNTAX PerceivedSeverityValue
        ACCESS read-only
        STATUS mandatory
        DESCRIPTION
            "The device is running in bootloader mode
             without a legal application software."
    ::= { orx2StatesEntry 18 }

    orx2StatesDefective OBJECT-TYPE
        SYNTAX PerceivedSeverityValue
        ACCESS read-only
        STATUS mandatory
        DESCRIPTION
            "The NEC has lost the connection to the device.
             Reason may be a removed or defective device.
             Note that this state is set by the NEC and not
             by the device"
    ::= { orx2StatesEntry 19 }

--*****************************************************************************************
--  orx2Control group

  orx2ControlTable OBJECT-TYPE
    SYNTAX SEQUENCE OF Orx2ControlEntry
    ACCESS not-accessible
    STATUS mandatory
    DESCRIPTION ""
  ::= { orx2Control 1 }

-- table of control entry(ro/rw)

  orx2ControlEntry OBJECT-TYPE
    SYNTAX Orx2ControlEntry
    ACCESS not-accessible
    STATUS mandatory
    DESCRIPTION "Alarms for a module."
    INDEX { orx2NESlot }
  ::= { orx2ControlTable 1 }

-- the structure of the entry

    Orx2ControlEntry ::= SEQUENCE
    {
        orx2ControlReset             TruthValue,
        orx2ControlModuleLedBlink    TruthValue
    }

    orx2ControlReset OBJECT-TYPE
      SYNTAX TruthValue
      ACCESS read-write
      STATUS mandatory
      DESCRIPTION "Reset the module."
    ::= { orx2ControlEntry 1 }

    orx2ControlModuleLedBlink OBJECT-TYPE
        SYNTAX TruthValue
        ACCESS read-write
        STATUS mandatory
        DESCRIPTION   "Writing this variable to true(1) lets the device's
        modul LED blink green for 10 seconds.
        Writing this variable to false(2) storx2 blinking at once.
        This variable always returns false(2) on read requests"
    ::= { orx2ControlEntry 2 }


--*****************************************************************************************
-- orx2Configuration group

    orx2ConfigurationTable OBJECT-TYPE
        SYNTAX SEQUENCE OF Orx2ConfigurationEntry
        ACCESS not-accessible
        STATUS mandatory
        DESCRIPTION ""
    ::= { orx2Configuration 1 }

-- table of configuration entry(ro/rw)

    orx2ConfigurationEntry OBJECT-TYPE
        SYNTAX Orx2ConfigurationEntry
        ACCESS not-accessible
        STATUS mandatory
        DESCRIPTION ""
        INDEX { orx2NESlot  }
    ::= { orx2ConfigurationTable 1 }

-- the structure of the entry

    Orx2ConfigurationEntry ::= SEQUENCE
    {
        -- Common
        orx2ConfigNESlotWrite                 NESlotWriteValue,
        orx2ConfigOutputMode                  OutputModeValue,
        orx2ConfigRedundancySetting           RedundancySettingValue,
        orx2ConfigLineCodeUsage               LinecodeModeValue,
        orx2ConfigRedundancyMode              RedundancyModeValue,
        -- Receiver 1
        orx2ConfigInputPwrLimitLoLo_Chn1      INTEGER,
        orx2ConfigInputPwrLimitLo_Chn1        INTEGER,
        orx2ConfigInputPwrLimitHi_Chn1        INTEGER,
        orx2ConfigInputPwrLimitHiHi_Chn1      INTEGER,
        orx2ConfigChannelActivate_Chn1        TruthValue,
        orx2ConfigIngressMode_Chn1            IngressModeValue,
        orx2ConfigRfOutputLevel_Chn1          RfOutputLevelValue,
        orx2ConfigExpectedLineCodeNumber_Chn1 LineCodeNumberValue,
        -- Receiver 2
        orx2ConfigInputPwrLimitLoLo_Chn2      INTEGER,
        orx2ConfigInputPwrLimitLo_Chn2        INTEGER,
        orx2ConfigInputPwrLimitHi_Chn2        INTEGER,
        orx2ConfigInputPwrLimitHiHi_Chn2      INTEGER,
        orx2ConfigChannelActivate_Chn2        TruthValue,
        orx2ConfigIngressMode_Chn2            IngressModeValue,
        orx2ConfigRfOutputLevel_Chn2          RfOutputLevelValue,
        orx2ConfigExpectedLineCodeNumber_Chn2 LineCodeNumberValue,
        -- Receiver 1
        orx2ConfigPilotRegulationMode_Chn1    PilotRegulationModeValue,
        orx2ConfigInputAttenDigits_Chn1       InputAttenDigitsValue,
        -- Receiver 2
        orx2ConfigPilotRegulationMode_Chn2    PilotRegulationModeValue,
        orx2ConfigInputAttenDigits_Chn2       InputAttenDigitsValue
    }

-- Common part

    orx2ConfigNESlotWrite OBJECT-TYPE
        SYNTAX NESlotWriteValue
        ACCESS read-write
        STATUS optional
        DESCRIPTION "By writing this variable a slot can be assigned
            for devices that dont support hardware slot detection.
            Reading '-1' means that the slot position is NOT writable."
    ::= { orx2ConfigurationEntry 1 }

    orx2ConfigOutputMode OBJECT-TYPE
        SYNTAX OutputModeValue
        ACCESS read-write
        STATUS mandatory
        DESCRIPTION
            "Selects the devices rf-output connection"
    ::= { orx2ConfigurationEntry 2 }

    orx2ConfigRedundancySetting OBJECT-TYPE
        SYNTAX RedundancySettingValue
        ACCESS read-write
        STATUS mandatory
        DESCRIPTION
            "Selects the devices redundancy behaviour"
    ::= { orx2ConfigurationEntry 3 }

    orx2ConfigLineCodeUsage OBJECT-TYPE
        SYNTAX LinecodeModeValue
        ACCESS read-write
        STATUS mandatory
        DESCRIPTION
            "Sets the usage of receive line codes"
    ::= { orx2ConfigurationEntry 4 }

    orx2ConfigRedundancyMode OBJECT-TYPE
        SYNTAX RedundancyModeValue
        ACCESS read-write
        STATUS mandatory
        DESCRIPTION
            "Set the devices redundancy mode. 
             Only writable if orx2ConfigLineCodeUsage != fullEnableLinecodes(1)
             Only used     if orx2ConfigRedundancySetting == deviceRedundancy(2)"
    ::= { orx2ConfigurationEntry 5 }

-- Receiver channel no.1

    orx2ConfigInputPwrLimitLoLo_Chn1 OBJECT-TYPE
        SYNTAX  INTEGER
        ACCESS  read-write
        STATUS  mandatory
        DESCRIPTION
            "The optical input power low alarm limit in 0.1 dBm units (Channel no.1)"
    ::={ orx2ConfigurationEntry 6 }

    orx2ConfigInputPwrLimitLo_Chn1 OBJECT-TYPE
        SYNTAX  INTEGER
        ACCESS  read-write
        STATUS  mandatory
        DESCRIPTION
            "The optical input power low warning limit in 0.1 dBm units (Channel no.1)"
    ::={ orx2ConfigurationEntry 7 }

    orx2ConfigInputPwrLimitHi_Chn1 OBJECT-TYPE
        SYNTAX  INTEGER
        ACCESS  read-write
        STATUS  mandatory
        DESCRIPTION
            "The optical input power high warning limit in 0.1 dBm units (Channel no.1)"
    ::={ orx2ConfigurationEntry 8 }

    orx2ConfigInputPwrLimitHiHi_Chn1 OBJECT-TYPE
        SYNTAX  INTEGER
        ACCESS  read-write
        STATUS  mandatory
        DESCRIPTION
            "The optical input power high alarm limit in 0.1 dBm units (Channel no.1)"
    ::={ orx2ConfigurationEntry 9 }

    orx2ConfigChannelActivate_Chn1 OBJECT-TYPE
        SYNTAX  TruthValue
        ACCESS  read-write
        STATUS  mandatory
        DESCRIPTION
            "Can be used to completely deactivate this receive channel. (Channel no.1)
             Used if one channel is not in use and should not rise any alarms."
    ::={ orx2ConfigurationEntry 10 }

    orx2ConfigIngressMode_Chn1 OBJECT-TYPE
        SYNTAX  IngressModeValue
        ACCESS  read-write
        STATUS  mandatory
        DESCRIPTION
            "Ingress attenuator settings. (Channel no.1)"
    ::={ orx2ConfigurationEntry 11 }

    orx2ConfigRfOutputLevel_Chn1 OBJECT-TYPE
        SYNTAX  RfOutputLevelValue
        ACCESS  read-write
        STATUS  mandatory
        DESCRIPTION
            "Rf output level settings. (Channel no.1)"
    ::={ orx2ConfigurationEntry 12 }

    orx2ConfigExpectedLineCodeNumber_Chn1 OBJECT-TYPE
        SYNTAX  LineCodeNumberValue
        ACCESS  read-write
        STATUS  mandatory
        DESCRIPTION
            "The expected remote transmitters line code number.
             An alarm rises if this value is diffent to the 
             received orx2DisplayRecvLineCodeNumber_Chn1 value.
             Only used if line codes are enabled."
    ::={ orx2ConfigurationEntry 13 }

-- Receiver channel no.2

    orx2ConfigInputPwrLimitLoLo_Chn2 OBJECT-TYPE
        SYNTAX  INTEGER
        ACCESS  read-write
        STATUS  mandatory
        DESCRIPTION
            "The optical input power low alarm limit in 0.1 dBm units (Channel no.2)"
    ::={ orx2ConfigurationEntry 14 }

    orx2ConfigInputPwrLimitLo_Chn2 OBJECT-TYPE
        SYNTAX  INTEGER
        ACCESS  read-write
        STATUS  mandatory
        DESCRIPTION
            "The optical input power low warning limit in 0.1 dBm units (Channel no.2)"
    ::={ orx2ConfigurationEntry 15 }

    orx2ConfigInputPwrLimitHi_Chn2 OBJECT-TYPE
        SYNTAX  INTEGER
        ACCESS  read-write
        STATUS  mandatory
        DESCRIPTION
            "The optical input power high warning limit in 0.1 dBm units (Channel no.2)"
    ::={ orx2ConfigurationEntry 16 }

    orx2ConfigInputPwrLimitHiHi_Chn2 OBJECT-TYPE
        SYNTAX  INTEGER
        ACCESS  read-write
        STATUS  mandatory
        DESCRIPTION
            "The optical input power high alarm limit in 0.1 dBm units (Channel no.2)"
    ::={ orx2ConfigurationEntry 17 }

    orx2ConfigChannelActivate_Chn2 OBJECT-TYPE
        SYNTAX  TruthValue
        ACCESS  read-write
        STATUS  mandatory
        DESCRIPTION
            "Can be used to completely deactivate this receive channel. (Channel no.2)
             Used if one channel is not in use and should not rise any alarms."
    ::={ orx2ConfigurationEntry 18 }

    orx2ConfigIngressMode_Chn2 OBJECT-TYPE
        SYNTAX  IngressModeValue
        ACCESS  read-write
        STATUS  mandatory
        DESCRIPTION
            "Ingress attenuator settings. (Channel no.2)"
    ::={ orx2ConfigurationEntry 19 }

    orx2ConfigRfOutputLevel_Chn2 OBJECT-TYPE
        SYNTAX  RfOutputLevelValue
        ACCESS  read-write
        STATUS  mandatory
        DESCRIPTION
            "Rf output level settings. (Channel no.2)"
    ::={ orx2ConfigurationEntry 20 }

    orx2ConfigExpectedLineCodeNumber_Chn2 OBJECT-TYPE
        SYNTAX  LineCodeNumberValue
        ACCESS  read-write
        STATUS  mandatory
        DESCRIPTION
            "The expected remote transmitters line code number.
             An alarm rises if this value is diffent to the 
             received orx2DisplayRecvLineCodeNumber_Chn2 value.
             Only used if line codes are enabled."
    ::={ orx2ConfigurationEntry 21 }

    orx2ConfigPilotRegulationMode_Chn1 OBJECT-TYPE
        SYNTAX  PilotRegulationModeValue
        ACCESS  read-write
        STATUS  mandatory
        DESCRIPTION
            "Pilot regulation settings. (Channel no.1)"
    ::={ orx2ConfigurationEntry 22 }

    orx2ConfigInputAttenDigits_Chn1 OBJECT-TYPE
        SYNTAX  InputAttenDigitsValue
        ACCESS  read-write
        STATUS  mandatory
        DESCRIPTION
            "The digits of the input attenuator (Channel no.1)
             Only needed, if pilot regulation disabled :
                'orx2ConfigPilotRegulationMode_Chn1' == 'regulationDisabled(1)' "
    ::={ orx2ConfigurationEntry 23 }

    orx2ConfigPilotRegulationMode_Chn2 OBJECT-TYPE
        SYNTAX  PilotRegulationModeValue
        ACCESS  read-write
        STATUS  mandatory
        DESCRIPTION
            "Pilot regulation settings. (Channel no.2)"
    ::={ orx2ConfigurationEntry 24 }

    orx2ConfigInputAttenDigits_Chn2 OBJECT-TYPE
        SYNTAX  InputAttenDigitsValue
        ACCESS  read-write
        STATUS  mandatory
        DESCRIPTION
            "The digits of the input attenuator (Channel no.2)
             Only needed, if pilot regulation disabled :
                'orx2ConfigPilotRegulationMode_Chn2' == 'regulationDisabled(1)' "
    ::={ orx2ConfigurationEntry 25 }


--*****************************************************************************************
-- Display group

    orx2DisplayTable OBJECT-TYPE
        SYNTAX SEQUENCE OF Orx2DisplayEntry
        ACCESS not-accessible
        STATUS mandatory
        DESCRIPTION ""
    ::= { orx2Display 1 }

-- table of configuration entry(ro/rw)

    orx2DisplayEntry OBJECT-TYPE
        SYNTAX Orx2DisplayEntry
        ACCESS not-accessible
        STATUS mandatory
        DESCRIPTION ""
        INDEX { orx2NESlot  }
    ::= { orx2DisplayTable 1 }

-- the structure of the entry

    Orx2DisplayEntry ::= SEQUENCE
    {
        orx2DisplayRecvLineCodeNumber_Chn1         LineCodeNumberValue,
        orx2DisplayRecvLineCodeNumber_Chn2         LineCodeNumberValue,
        orx2DisplayRecvLineCodeNomRedFlag_Chn1     LineCodeRcvdNomRedFlagValue,
        orx2DisplayRecvLineCodeNomRedFlag_Chn2     LineCodeRcvdNomRedFlagValue,
        orx2DisplaySleeping_Chn1                   TruthValue,
        orx2DisplaySleeping_Chn2                   TruthValue
    }

    orx2DisplayRecvLineCodeNumber_Chn1 OBJECT-TYPE
        SYNTAX LineCodeNumberValue
        ACCESS read-only
        STATUS mandatory
        DESCRIPTION
            "The received line code number of the remote transmitter (Channel no.1)."
      ::= { orx2DisplayEntry 1 }

    orx2DisplayRecvLineCodeNumber_Chn2 OBJECT-TYPE
        SYNTAX LineCodeNumberValue
        ACCESS read-only
        STATUS mandatory
        DESCRIPTION
            "The received line code number of the remote transmitter (Channel no.2)."
      ::= { orx2DisplayEntry 2 }

    orx2DisplayRecvLineCodeNomRedFlag_Chn1 OBJECT-TYPE
        SYNTAX LineCodeRcvdNomRedFlagValue
        ACCESS read-only
        STATUS mandatory
        DESCRIPTION
            "The received line code nominal/redundant flag sent by remote 
             transmitter (Channel no.1)."
      ::= { orx2DisplayEntry 3 }

    orx2DisplayRecvLineCodeNomRedFlag_Chn2 OBJECT-TYPE
        SYNTAX LineCodeRcvdNomRedFlagValue
        ACCESS read-only
        STATUS mandatory
        DESCRIPTION
            "The received line code nominal/redundant flag sent by remote 
             transmitter (Channel no.2)."
      ::= { orx2DisplayEntry 4 }

    orx2DisplaySleeping_Chn1 OBJECT-TYPE
        SYNTAX TruthValue
        ACCESS read-only
        STATUS mandatory
        DESCRIPTION
            "Indicates if the receiver channel no.1 is in sleeping state."
      ::= { orx2DisplayEntry 5 }

    orx2DisplaySleeping_Chn2 OBJECT-TYPE
        SYNTAX TruthValue
        ACCESS read-only
        STATUS mandatory
        DESCRIPTION
            "Indicates if the receiver channel no.2 is in sleeping state."
      ::= { orx2DisplayEntry 6 }



--*****************************************************************************************
END
