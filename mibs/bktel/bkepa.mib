-- *********************************************************************************************
-- *
-- * Description:   Implements definitions for the Epa-modul
-- *
-- * Copyright 2004 by BKtel communications GmbH
-- *
-- *     V.0.1 18.08.04  M. Heldmann first draft
-- *     V.0.2 11.09.04  M. Heldmann added epaStatesRfAttenLimit and epaStatesRedundantActivated 
-- *     V.0.3 17.09.04  M. Heldmann marked epaControlStandby as FOR FUTURE USE 
-- *     V.1.0 28.01.05  M. Heldmann epaStatesRedundantActivated renamed to epaStatesRedundancyActivated and description changed
-- *                                 epaStatesStandby renamed to epaStatesSleeping, epaStatesIsRedundantDevice added
-- *     V.1.1 04.10.06  M. Heldmann NESlotWriteValue expanded due to new 2G6 platform needs
-- *     V.1.2 29.05.08  M. Heldmann renamed threshold parameters in xxxxMeasuringValuesTable
-- *     V.1.3 20.06.08  M. Heldmann renamed epaControlStandby to epaControlActivityMode and expanded epaControlActivityMode (full compatible)
-- *                                 added epaDisplayRedundancySupported,epaDisplayDeviceRedundancyState,epaDisplayDeviceActivity
-- *                                 epaStatesRedundancyActivated and epaStatesIsRedundantDevice no more used and marked as obsolete
-- *                                 added epaStatesRedundancySwitch
-- *     V.1.4 11.07.13  M. Heldmann adjusted syntax of "CommonEntry" to remove MIB compiler warnings
-- *     V.1.5 05.09.14  M. Heldmann changed CommonModuleWidth and ConfigNESlotWrite STATUS to optional
-- *********************************************************************************************

BKTEL-HFC862-EPA-V01-MIB DEFINITIONS ::= BEGIN

    IMPORTS
        experimental, enterprises, TimeTicks, IpAddress, Counter
                 FROM RFC1155-SMI
    OBJECT-TYPE
                 FROM RFC-1212
        TRAP-TYPE
                 FROM RFC-1215
        modules, DisplayString, TruthValue, PerceivedSeverityValue, NESlotValue, ModuleWidthValue
                 FROM   BKTEL-HFC862-BASE-MIB
    ;

    epa                  OBJECT IDENTIFIER ::= { modules 110}
    epaCommon            OBJECT IDENTIFIER ::= { epa 1 }
    epaStates            OBJECT IDENTIFIER ::= { epa 2 }
    epaConfiguration     OBJECT IDENTIFIER ::= { epa 3 }
    epaControl           OBJECT IDENTIFIER ::= { epa 4 }
    epaMeasuringValues   OBJECT IDENTIFIER ::= { epa 5 }
    epaDisplay           OBJECT IDENTIFIER ::= { epa 6 }


--
-- Type definitions
--

        AgcMode ::= INTEGER
            {
            modeAgcOff(1),
            modeAgcOn(2)
            }

        RfMode ::= INTEGER
            {
            modeNormal(1),
            modeLowNoise(2),
            modeLowDistortion(3)
            }

        RedundancyMode ::= INTEGER
            {
            modeNoRedundancy(1),
            modeNominalDevice(2),
            modeRedundantDevice(3),
            modeAutoDetectBySlot(4)
            }

        DeviceActivityMode ::= INTEGER
            {
            forceStandby(1),
            alwaysActive(2),
            automatic(3)
            }

        DeviceActivityState ::= INTEGER
            {
            standby(1),
            active(2)
            }

        DeviceRedundancyState ::= INTEGER
            {
            nominalDevice(1),
            redundantDevice(2)
            }

        NESlotWriteValue ::= INTEGER (-1..99)


--*****************************************************************************************
-- EPA ( Optical Transmitter with design release V01 )

--*****************************************************************************************
-- epaCommon group

    epaCommonNumberOfModules OBJECT-TYPE
        SYNTAX  INTEGER(0..50)
        ACCESS  read-only
        STATUS  mandatory
        DESCRIPTION "Number of modules in table."
    ::= { epaCommon 1 }

    epaCommonTable OBJECT-TYPE
        SYNTAX SEQUENCE OF EpaCommonEntry
        ACCESS not-accessible
        STATUS mandatory
        DESCRIPTION "The table contains all modules of the EPA-type in the NE"
    ::= { epaCommon 2 }

-- table of states entry(ro/rw)

    epaCommonEntry OBJECT-TYPE
        SYNTAX EpaCommonEntry
        ACCESS not-accessible
        STATUS mandatory
        DESCRIPTION "Common-Values for a module."
        INDEX { epaNESlot }
    ::= { epaCommonTable 1 }

-- the structure of the entry

    EpaCommonEntry ::= SEQUENCE
    {
        epaNESlot                      NESlotValue,
        epaCommonType                  DisplayString,
        epaCommonDescr                 DisplayString,
        epaCommonFirmwareId            DisplayString,
        epaCommonModuleWidth           ModuleWidthValue
    }

    epaNESlot OBJECT-TYPE
        SYNTAX  NESlotValue
        ACCESS  read-only
        STATUS  mandatory
        DESCRIPTION
        "The slot number of the chassis for which this
        entry contains management information.
        Equal to: modEPAv11UniqueID"
    ::= { epaCommonEntry 1 }

    epaCommonType OBJECT-TYPE
        SYNTAX  DisplayString  (SIZE(0..32))
        ACCESS  read-only
        STATUS  mandatory
        DESCRIPTION
        "The type of physical module. modSlotEmpty indicates
         an empty slot.  A Value of modSlotUnknown indicates
         that the type of module is unknown."
    ::= { epaCommonEntry 2 }

    epaCommonDescr OBJECT-TYPE
        SYNTAX  DisplayString
        ACCESS  read-write
        STATUS  mandatory
        DESCRIPTION
        "A textual description of the module.
        If not available, this Value should be
        set to a zero length string."
    ::= { epaCommonEntry 3 }

    epaCommonFirmwareId OBJECT-TYPE
        SYNTAX DisplayString (SIZE(0..32))
        ACCESS read-only
        STATUS mandatory
        DESCRIPTION "The firmware Id of the module."
    ::= { epaCommonEntry 4 }

    epaCommonModuleWidth OBJECT-TYPE
        SYNTAX ModuleWidthValue
        ACCESS read-only
        STATUS optional
        DESCRIPTION "The width of the module in multiples of slots (1, 2, ...)"
    ::= { epaCommonEntry 5 }

--*****************************************************************************************
-- epaMeasuringValues group

-- table of measuring Values

    epaMeasuringValuesTable OBJECT-TYPE
        SYNTAX SEQUENCE OF EpaMeasuringValuesEntry
        ACCESS not-accessible
        STATUS mandatory
        DESCRIPTION ""
    ::= { epaMeasuringValues 1 }

-- table of measuring Values entry

    epaMeasuringValuesEntry OBJECT-TYPE
        SYNTAX EpaMeasuringValuesEntry
        ACCESS not-accessible
        STATUS mandatory
        DESCRIPTION "Common-Values for a module."
        INDEX { epaNESlot }
    ::= { epaMeasuringValuesTable 1 }

--  the structure of the entry

    EpaMeasuringValuesEntry ::= SEQUENCE
    {
        epaRfInputLoLo                 INTEGER,
        epaRfInputLo                   INTEGER,
        epaRfInputValue                INTEGER,
        epaRfInputHi                   INTEGER,
        epaRfInputHiHi                 INTEGER,

        epaRfOutputLoLo                INTEGER,
        epaRfOutputLo                  INTEGER,
        epaRfOutputValue               INTEGER,
        epaRfOutputHi                  INTEGER,
        epaRfOutputHiHi                INTEGER,

        epaRfGainReadLoLo              INTEGER,
        epaRfGainReadLo                INTEGER,
        epaRfGainReadValue             INTEGER,
        epaRfGainReadHi                INTEGER,
        epaRfGainReadHiHi              INTEGER,

        epaPlus3p3VLoLo                INTEGER,
        epaPlus3p3VLo                  INTEGER,
        epaPlus3p3VValue               INTEGER,
        epaPlus3p3VHi                  INTEGER,
        epaPlus3p3VHiHi                INTEGER,

        epaPlus5VLoLo                  INTEGER,
        epaPlus5VLo                    INTEGER,
        epaPlus5VValue                 INTEGER,
        epaPlus5VHi                    INTEGER,
        epaPlus5VHiHi                  INTEGER,

        epaPlus24VLoLo                 INTEGER,
        epaPlus24VLo                   INTEGER,
        epaPlus24VValue                INTEGER,
        epaPlus24VHi                   INTEGER,
        epaPlus24VHiHi                 INTEGER,

        epaTemperatureLoLo             INTEGER,
        epaTemperatureLo               INTEGER,
        epaTemperatureValue            INTEGER,
        epaTemperatureHi               INTEGER,
        epaTemperatureHiHi             INTEGER
    }

-- *****
    epaRfInputLoLo OBJECT-TYPE
        SYNTAX INTEGER
        ACCESS read-only
        STATUS mandatory
        DESCRIPTION "RfInput (total rms) low alarm threshold in steps of 0.1 dBm."
    ::= { epaMeasuringValuesEntry 1 }

    epaRfInputLo OBJECT-TYPE
        SYNTAX INTEGER
        ACCESS read-only
        STATUS mandatory
        DESCRIPTION "RfInput (total rms) low warning threshold in steps of 0.1 dBm."
    ::= { epaMeasuringValuesEntry 2 }

    epaRfInputValue OBJECT-TYPE
        SYNTAX INTEGER
        ACCESS read-only
        STATUS mandatory
        DESCRIPTION "RfInput (total rms) in steps of 0.1 dBm."
    ::= { epaMeasuringValuesEntry 3 }

    epaRfInputHi OBJECT-TYPE
        SYNTAX INTEGER
        ACCESS read-only
        STATUS mandatory
        DESCRIPTION "RfInput (total rms) high warning threshold in steps of 0.1 dBm."
    ::= { epaMeasuringValuesEntry 4 }

    epaRfInputHiHi OBJECT-TYPE
        SYNTAX INTEGER
        ACCESS read-only
        STATUS mandatory
        DESCRIPTION "RfInput (total rms) high alarm threshold in steps of 0.1 dBm."
    ::= { epaMeasuringValuesEntry 5 }

-- *****
    epaRfOutputLoLo OBJECT-TYPE
        SYNTAX INTEGER
        ACCESS read-only
        STATUS mandatory
        DESCRIPTION "RfOutput (total rms) low alarm threshold in steps of 0.1 dBm."
    ::= { epaMeasuringValuesEntry 6 }

    epaRfOutputLo OBJECT-TYPE
        SYNTAX INTEGER
        ACCESS read-only
        STATUS mandatory
        DESCRIPTION "RfOutput (total rms) low warning threshold in steps of 0.1 dBm."
    ::= { epaMeasuringValuesEntry 7 }

    epaRfOutputValue OBJECT-TYPE
        SYNTAX INTEGER
        ACCESS read-only
        STATUS mandatory
        DESCRIPTION "RfOutput (total rms) in steps of 0.1 dBm."
    ::= { epaMeasuringValuesEntry 8 }

    epaRfOutputHi OBJECT-TYPE
        SYNTAX INTEGER
        ACCESS read-only
        STATUS mandatory
        DESCRIPTION "RfOutput (total rms) high warning threshold in steps of 0.1 dBm."
    ::= { epaMeasuringValuesEntry 9 }

    epaRfOutputHiHi OBJECT-TYPE
        SYNTAX INTEGER
        ACCESS read-only
        STATUS mandatory
        DESCRIPTION "RfOutput (total rms) high alarm threshold in steps of 0.1 dBm."
    ::= { epaMeasuringValuesEntry 10 }

-- *****
    epaRfGainReadLoLo OBJECT-TYPE
        SYNTAX INTEGER
        ACCESS read-only
        STATUS mandatory
        DESCRIPTION "rf gain low alarm threshold in steps of 0.1 dB."
    ::= { epaMeasuringValuesEntry 11 }

    epaRfGainReadLo OBJECT-TYPE
        SYNTAX INTEGER
        ACCESS read-only
        STATUS mandatory
        DESCRIPTION "rf gain low warning threshold in steps of 0.1 dB."
    ::= { epaMeasuringValuesEntry 12 }

    epaRfGainReadValue OBJECT-TYPE
        SYNTAX INTEGER
        ACCESS read-only
        STATUS mandatory
        DESCRIPTION "rf gain in steps of 0.1 dB."
    ::= { epaMeasuringValuesEntry 13 }

    epaRfGainReadHi OBJECT-TYPE
        SYNTAX INTEGER
        ACCESS read-only
        STATUS mandatory
        DESCRIPTION "rf gain high warning threshold in steps of 0.1 dB."
    ::= { epaMeasuringValuesEntry 14 }

    epaRfGainReadHiHi OBJECT-TYPE
        SYNTAX INTEGER
        ACCESS read-only
        STATUS mandatory
        DESCRIPTION "rf gain high alarm threshold in steps of 0.1 dB."
    ::= { epaMeasuringValuesEntry 15 }

-- *****
    epaPlus3p3VLoLo OBJECT-TYPE
        SYNTAX INTEGER
        ACCESS read-only
        STATUS mandatory
        DESCRIPTION "The +3.3V internal voltage low alarm threshold in steps of 0.1V."
    ::= { epaMeasuringValuesEntry 16 }

    epaPlus3p3VLo OBJECT-TYPE
        SYNTAX INTEGER
        ACCESS read-only
        STATUS mandatory
        DESCRIPTION "The +3.3V internal voltage low warning threshold in steps of 0.1V."
    ::= { epaMeasuringValuesEntry 17 }

    epaPlus3p3VValue OBJECT-TYPE
        SYNTAX INTEGER
        ACCESS read-only
        STATUS mandatory
        DESCRIPTION "The +3.3V internal voltage in steps of 0.1V."
    ::= { epaMeasuringValuesEntry 18 }

    epaPlus3p3VHi OBJECT-TYPE
        SYNTAX INTEGER
        ACCESS read-only
        STATUS mandatory
        DESCRIPTION "The +3.3V internal voltage high warning threshold in steps of 0.1V."
    ::= { epaMeasuringValuesEntry 19 }

    epaPlus3p3VHiHi OBJECT-TYPE
        SYNTAX INTEGER
        ACCESS read-only
        STATUS mandatory
        DESCRIPTION "The +3.3V internal voltage high alarm threshold in steps of 0.1V."
    ::= { epaMeasuringValuesEntry 20 }

-- *****
    epaPlus5VLoLo OBJECT-TYPE
        SYNTAX INTEGER
        ACCESS read-only
        STATUS mandatory
        DESCRIPTION "The +5V internal voltage low alarm threshold in steps of 0.1V."
    ::= { epaMeasuringValuesEntry 21 }

    epaPlus5VLo OBJECT-TYPE
        SYNTAX INTEGER
        ACCESS read-only
        STATUS mandatory
        DESCRIPTION "The +5V internal voltage low warning threshold in steps of 0.1V."
    ::= { epaMeasuringValuesEntry 22 }

    epaPlus5VValue OBJECT-TYPE
        SYNTAX INTEGER
        ACCESS read-only
        STATUS mandatory
        DESCRIPTION "The +5V internal voltage in steps of 0.1V."
    ::= { epaMeasuringValuesEntry 23 }

    epaPlus5VHi OBJECT-TYPE
        SYNTAX INTEGER
        ACCESS read-only
        STATUS mandatory
        DESCRIPTION "The +5V internal voltage high warning threshold in steps of 0.1V."
    ::= { epaMeasuringValuesEntry 24 }

    epaPlus5VHiHi OBJECT-TYPE
        SYNTAX INTEGER
        ACCESS read-only
        STATUS mandatory
        DESCRIPTION "The +5V internal voltage high alarm threshold in steps of 0.1V."
    ::= { epaMeasuringValuesEntry 25 }

-- *****
    epaPlus24VLoLo OBJECT-TYPE
        SYNTAX INTEGER
        ACCESS read-only
        STATUS mandatory
        DESCRIPTION "The +24V supply voltage low alarm threshold in steps of 0.1V."
    ::= { epaMeasuringValuesEntry 26 }

    epaPlus24VLo OBJECT-TYPE
        SYNTAX INTEGER
        ACCESS read-only
        STATUS mandatory
        DESCRIPTION "The +24V supply voltage low warning threshold in steps of 0.1V."
    ::= { epaMeasuringValuesEntry 27 }

    epaPlus24VValue OBJECT-TYPE
        SYNTAX INTEGER
        ACCESS read-only
        STATUS mandatory
        DESCRIPTION "The +24V supply voltage in steps of 0.1V."
    ::= { epaMeasuringValuesEntry 28 }

    epaPlus24VHi OBJECT-TYPE
        SYNTAX INTEGER
        ACCESS read-only
        STATUS mandatory
        DESCRIPTION "The +24V supply voltage high warning threshold in steps of 0.1V."
    ::= { epaMeasuringValuesEntry 29 }

    epaPlus24VHiHi OBJECT-TYPE
        SYNTAX INTEGER
        ACCESS read-only
        STATUS mandatory
        DESCRIPTION "The +24V supply voltage high alarm threshold in steps of 0.1V."
    ::= { epaMeasuringValuesEntry 30 }

-- *****
     epaTemperatureLoLo OBJECT-TYPE
        SYNTAX INTEGER
        ACCESS read-only
        STATUS mandatory
        DESCRIPTION "The module temperature low alarm threshold in steps of 0.1 celsius degrees."
    ::= { epaMeasuringValuesEntry 31 }

    epaTemperatureLo OBJECT-TYPE
        SYNTAX INTEGER
        ACCESS read-only
        STATUS mandatory
        DESCRIPTION "The module temperature low warning threshold in steps of 0.1 celsius degrees."
    ::= { epaMeasuringValuesEntry 32 }

    epaTemperatureValue OBJECT-TYPE
        SYNTAX INTEGER
        ACCESS read-only
        STATUS mandatory
        DESCRIPTION "The module temperature in steps of 0.1 celsius degrees."
    ::= { epaMeasuringValuesEntry 33 }

    epaTemperatureHi OBJECT-TYPE
        SYNTAX INTEGER
        ACCESS read-only
        STATUS mandatory
        DESCRIPTION "The module temperature high warning threshold in steps of 0.1 celsius degrees."
    ::= { epaMeasuringValuesEntry 34 }

    epaTemperatureHiHi OBJECT-TYPE
        SYNTAX INTEGER
        ACCESS read-only
        STATUS mandatory
        DESCRIPTION "The module temperature high alarm threshold in steps of 0.1 celsius degrees."
    ::= { epaMeasuringValuesEntry 35 }


--*****************************************************************************************
--  epaStates group

-- Note: For every control OId there must be a correspondant alarm OId!

    epaStatesTable OBJECT-TYPE
        SYNTAX SEQUENCE OF EpaStatesEntry
        ACCESS not-accessible
        STATUS mandatory
        DESCRIPTION ""
    ::= { epaStates 1 }

-- table of states entry(ro/rw)

    epaStatesEntry OBJECT-TYPE
        SYNTAX EpaStatesEntry
        ACCESS not-accessible
        STATUS mandatory
        DESCRIPTION "Alarms for a module."
        INDEX { epaNESlot }
    ::= { epaStatesTable 1 }

-- the structure of the entry

    EpaStatesEntry ::= SEQUENCE
    {
        epaStatesBootloader          PerceivedSeverityValue,
        epaStatesCommLoss            PerceivedSeverityValue,
        epaStatesInitializing        PerceivedSeverityValue,
        epaStatesSleeping            PerceivedSeverityValue,
        epaStatesTemperatureLow      PerceivedSeverityValue,
        epaStatesTemperatureHigh     PerceivedSeverityValue,
        epaStatesInputLow            PerceivedSeverityValue,
        epaStatesInputHigh           PerceivedSeverityValue,
        epaStatesOutputLow           PerceivedSeverityValue,
        epaStatesOutputHigh          PerceivedSeverityValue,
        epaStatesRfGainReadLow       PerceivedSeverityValue,
        epaStatesRfGainReadHigh      PerceivedSeverityValue,
        epaStatesPlus3p3VLow         PerceivedSeverityValue,
        epaStatesPlus3p3VHigh        PerceivedSeverityValue,
        epaStatesPlus5VLow           PerceivedSeverityValue,
        epaStatesPlus5VHigh          PerceivedSeverityValue,
        epaStatesPlus24VLow          PerceivedSeverityValue,
        epaStatesPlus24VHigh         PerceivedSeverityValue,
        epaStatesSlotDetection       PerceivedSeverityValue,
        epaStatesRfAttenLimit        PerceivedSeverityValue,
        epaStatesObsolete1           PerceivedSeverityValue, -- epaStatesRedundancyActivated
        epaStatesObsolete2           PerceivedSeverityValue, -- epaStatesIsRedundantDevice
        epaStatesRedundancySwitch    PerceivedSeverityValue
    }

    epaStatesBootloader OBJECT-TYPE
        SYNTAX PerceivedSeverityValue
        ACCESS read-only
        STATUS mandatory
        DESCRIPTION
            "The device is running in bootloader mode
             without a legal application software."
    ::= { epaStatesEntry 1 }

    epaStatesCommLoss OBJECT-TYPE
        SYNTAX PerceivedSeverityValue
        ACCESS read-only
        STATUS mandatory
        DESCRIPTION
            "The NEC has lost the connection to the device.
             Reason may be a removed or defective device.
             Note that this state is set by the NEC and not
             by the device"
    ::= { epaStatesEntry 2 }

    epaStatesInitializing OBJECT-TYPE
        SYNTAX PerceivedSeverityValue
        ACCESS read-only
        STATUS mandatory
        DESCRIPTION "The device is initializing"
    ::= { epaStatesEntry 3 }

    epaStatesSleeping OBJECT-TYPE
        SYNTAX PerceivedSeverityValue
        ACCESS read-only
        STATUS mandatory
        DESCRIPTION "Device is sleeping, no rf output"
    ::= { epaStatesEntry 4 }

    epaStatesTemperatureLow OBJECT-TYPE
        SYNTAX PerceivedSeverityValue
        ACCESS read-only
        STATUS mandatory
        DESCRIPTION "Device internal temperature low"
    ::= { epaStatesEntry 5 }

    epaStatesTemperatureHigh OBJECT-TYPE
        SYNTAX PerceivedSeverityValue
        ACCESS read-only
        STATUS mandatory
        DESCRIPTION "Device internal temperature high"
    ::= { epaStatesEntry 6 }

    epaStatesInputLow OBJECT-TYPE
        SYNTAX PerceivedSeverityValue
        ACCESS read-only
        STATUS mandatory
        DESCRIPTION "rf input (total rms) low"
    ::= { epaStatesEntry 7 }

    epaStatesInputHigh OBJECT-TYPE
        SYNTAX PerceivedSeverityValue
        ACCESS read-only
        STATUS mandatory
        DESCRIPTION "rf input (total rms) high"
    ::= { epaStatesEntry 8 }

    epaStatesOutputLow OBJECT-TYPE
        SYNTAX PerceivedSeverityValue
        ACCESS read-only
        STATUS mandatory
        DESCRIPTION "rf output (total rms) low"
    ::= { epaStatesEntry 9 }

    epaStatesOutputHigh OBJECT-TYPE
        SYNTAX PerceivedSeverityValue
        ACCESS read-only
        STATUS mandatory
        DESCRIPTION "rf output (total rms) high"
    ::= { epaStatesEntry 10 }

    epaStatesRfGainReadLow OBJECT-TYPE
        SYNTAX PerceivedSeverityValue
        ACCESS read-only
        STATUS mandatory
        DESCRIPTION "Rf gain low"
    ::= { epaStatesEntry 11 }

    epaStatesRfGainReadHigh OBJECT-TYPE
        SYNTAX PerceivedSeverityValue
        ACCESS read-only
        STATUS mandatory
        DESCRIPTION "Rf gain high"
    ::= { epaStatesEntry 12 }

    epaStatesPlus3p3VLow OBJECT-TYPE
        SYNTAX PerceivedSeverityValue
        ACCESS read-only
        STATUS mandatory
        DESCRIPTION "3.3 Volt supply low"
    ::= { epaStatesEntry 13 }

    epaStatesPlus3p3VHigh OBJECT-TYPE
        SYNTAX PerceivedSeverityValue
        ACCESS read-only
        STATUS mandatory
        DESCRIPTION "3.3 Volt supply high"
    ::= { epaStatesEntry 14 }

    epaStatesPlus5VLow OBJECT-TYPE
        SYNTAX PerceivedSeverityValue
        ACCESS read-only
        STATUS mandatory
        DESCRIPTION "5 Volt supply low"
    ::= { epaStatesEntry 15 }

    epaStatesPlus5VHigh OBJECT-TYPE
        SYNTAX PerceivedSeverityValue
        ACCESS read-only
        STATUS mandatory
        DESCRIPTION "5 Volt supply high"
    ::= { epaStatesEntry 16 }

    epaStatesPlus24VLow OBJECT-TYPE
        SYNTAX PerceivedSeverityValue
        ACCESS read-only
        STATUS mandatory
        DESCRIPTION "24 Volt supply low"
    ::= { epaStatesEntry 17 }

    epaStatesPlus24VHigh OBJECT-TYPE
        SYNTAX PerceivedSeverityValue
        ACCESS read-only
        STATUS mandatory
        DESCRIPTION "24 Volt supply high"
    ::= { epaStatesEntry 18 }

    epaStatesSlotDetection OBJECT-TYPE
        SYNTAX PerceivedSeverityValue
        ACCESS read-only
        STATUS mandatory
        DESCRIPTION "Slot detection not possible"
    ::= { epaStatesEntry 19 }

    epaStatesRfAttenLimit OBJECT-TYPE
        SYNTAX PerceivedSeverityValue
        ACCESS read-only
        STATUS mandatory
        DESCRIPTION "RF attenuator limit reached"
    ::= { epaStatesEntry 20 }

    epaStatesObsolete1 OBJECT-TYPE
        SYNTAX PerceivedSeverityValue
        ACCESS read-only
        STATUS mandatory
        DESCRIPTION "Obsolete - Always returns clear(5)"
    ::= { epaStatesEntry 21 }

    epaStatesObsolete2 OBJECT-TYPE
        SYNTAX PerceivedSeverityValue
        ACCESS read-only
        STATUS mandatory
        DESCRIPTION "Obsolete - Always returns clear(5)"
    ::= { epaStatesEntry 22 }

    epaStatesRedundancySwitch OBJECT-TYPE
        SYNTAX PerceivedSeverityValue
        ACCESS read-only
        STATUS mandatory
        DESCRIPTION "This (redundant) device has been activated (redundancy switchover)"
    ::= { epaStatesEntry 23 }


--*****************************************************************************************
--  epaControl group

    epaControlTable OBJECT-TYPE
        SYNTAX SEQUENCE OF EpaControlEntry
        ACCESS not-accessible
        STATUS mandatory
        DESCRIPTION ""
    ::= { epaControl 1 }

-- table of control entry(ro/rw)

    epaControlEntry OBJECT-TYPE
        SYNTAX EpaControlEntry
        ACCESS not-accessible
        STATUS mandatory
        DESCRIPTION "Alarms for a module."
        INDEX { epaNESlot }
    ::= { epaControlTable 1 }

-- the structure of the entry

    EpaControlEntry ::= SEQUENCE
    {
        epaControlActivityMode     DeviceActivityMode,
        epaControlReset            TruthValue,
        epaControlModuleLedBlink   TruthValue
    }

    epaControlActivityMode OBJECT-TYPE
        SYNTAX DeviceActivityMode
        ACCESS read-write
        STATUS mandatory
        DESCRIPTION 
            "Device's activity mode.
             Note that elder devices only support the alwaysActive(2) mode,
             a set request to other modes results in a BadValue response here"
    ::= { epaControlEntry 1 }

    epaControlReset OBJECT-TYPE
      SYNTAX TruthValue
      ACCESS read-write
      STATUS mandatory
      DESCRIPTION "Reset the module."
    ::= { epaControlEntry 2 }

    epaControlModuleLedBlink OBJECT-TYPE
        SYNTAX TruthValue
        ACCESS read-write
        STATUS mandatory
        DESCRIPTION "Writing this variable to true(1) lets the device's
        modul LED blink green for 10 seconds.
        Writing this variable to false(2) stops blinking at once.
        This variable always returns false(2) on read requests"
    ::= { epaControlEntry 3 }

--*****************************************************************************************
-- epaConfiguration group

    epaConfigurationTable OBJECT-TYPE
        SYNTAX SEQUENCE OF EpaConfigurationEntry
        ACCESS not-accessible
        STATUS mandatory
        DESCRIPTION ""
    ::= { epaConfiguration 1 }

-- table of configuration entry(ro/rw)

    epaConfigurationEntry OBJECT-TYPE
        SYNTAX EpaConfigurationEntry
        ACCESS not-accessible
        STATUS mandatory
        DESCRIPTION ""
        INDEX { epaNESlot  }
    ::= { epaConfigurationTable 1 }

-- the structure of the entry

    EpaConfigurationEntry ::= SEQUENCE
    {
        epaConfigNESlotWrite         NESlotWriteValue,
        epaConfigAgcMode             AgcMode,
        epaConfigRfMode              RfMode,
        epaConfigRfGain              INTEGER,
        epaConfigRfGainLimit         INTEGER,
        epaConfigSlope               INTEGER,
        epaConfigRfOutputAdj         INTEGER,
        epaConfigRedundancyMode      RedundancyMode,

        epaConfigRfInputLimitLoLo    INTEGER,
        epaConfigRfInputLimitLo      INTEGER,
        epaConfigRfInputLimitHi      INTEGER,
        epaConfigRfInputLimitHiHi    INTEGER,

        epaConfigRfGainReadLimitLoLo INTEGER,
        epaConfigRfGainReadLimitLo   INTEGER,
        epaConfigRfGainReadLimitHi   INTEGER,
        epaConfigRfGainReadLimitHiHi INTEGER,

        epaConfigRfOutputLimitLoLo   INTEGER,
        epaConfigRfOutputLimitLo     INTEGER,
        epaConfigRfOutputLimitHi     INTEGER,
        epaConfigRfOutputLimitHiHi   INTEGER
    }

    epaConfigNESlotWrite OBJECT-TYPE
        SYNTAX NESlotWriteValue
        ACCESS read-write
        STATUS optional
        DESCRIPTION "By writing this variable a slot can be assigned
            for devices that dont support hardware slot detection.
            Reading '-1' means that the slot position is NOT writable."
   ::= { epaConfigurationEntry 1 }

    epaConfigAgcMode OBJECT-TYPE
        SYNTAX AgcMode
        ACCESS read-write
        STATUS mandatory
        DESCRIPTION "The AGC mode."
    ::= { epaConfigurationEntry 2 }

    epaConfigRfMode OBJECT-TYPE
        SYNTAX RfMode
        ACCESS read-write
        STATUS mandatory
        DESCRIPTION "The rf mode."
    ::= { epaConfigurationEntry 3 }

    epaConfigRfGain OBJECT-TYPE
        SYNTAX INTEGER
        ACCESS read-write
        STATUS mandatory
        DESCRIPTION "The desired offset from nominal gain in 0.1 dB units.
            This parameter is only used if AGC is off."
    ::= { epaConfigurationEntry 4 }

    epaConfigRfGainLimit OBJECT-TYPE
        SYNTAX INTEGER
        ACCESS read-write
        STATUS mandatory
        DESCRIPTION "The maximum offset from nominal gain in 0.1 dB units.
            This parameter is only used if AGC is off."
    ::= { epaConfigurationEntry 5 }

    epaConfigSlope OBJECT-TYPE
        SYNTAX INTEGER
        ACCESS read-write
        STATUS mandatory
        DESCRIPTION "The desired slope in 0.1 dB units."
    ::= { epaConfigurationEntry 6 }

    epaConfigRfOutputAdj OBJECT-TYPE
        SYNTAX INTEGER
        ACCESS read-write
        STATUS mandatory
        DESCRIPTION "The desired rf output power in 0.1 dB units."
    ::= { epaConfigurationEntry 7 }

    epaConfigRedundancyMode OBJECT-TYPE
        SYNTAX RedundancyMode
        ACCESS read-write
        STATUS mandatory
        DESCRIPTION "The redundancy mode."
    ::= { epaConfigurationEntry 8 }

-- *****
    epaConfigRfInputLimitLoLo OBJECT-TYPE
        SYNTAX  INTEGER
        ACCESS  read-write
        STATUS  mandatory
        DESCRIPTION
            "The rf input power low alarm limit in 0.1 dBm units"
    ::={ epaConfigurationEntry 9 }

    epaConfigRfInputLimitLo OBJECT-TYPE
        SYNTAX  INTEGER
        ACCESS  read-write
        STATUS  mandatory
        DESCRIPTION
            "The rf input power low warning limit in 0.1 dBm units"
    ::={ epaConfigurationEntry 10 }

    epaConfigRfInputLimitHi OBJECT-TYPE
        SYNTAX  INTEGER
        ACCESS  read-write
        STATUS  mandatory
        DESCRIPTION
            "The rf input power high warning limit in 0.1 dBm units"
    ::={ epaConfigurationEntry 11 }

    epaConfigRfInputLimitHiHi OBJECT-TYPE
        SYNTAX  INTEGER
        ACCESS  read-write
        STATUS  mandatory
        DESCRIPTION
            "The rf input power high alarm limit in 0.1 dBm units"
    ::={ epaConfigurationEntry 12 }

-- *****
    epaConfigRfGainReadLimitLoLo OBJECT-TYPE
        SYNTAX  INTEGER
        ACCESS  read-write
        STATUS  mandatory
        DESCRIPTION
            "The rf gain low alarm limit in 0.1 dB units (in AGC ON mode)"
    ::={ epaConfigurationEntry 13 }

    epaConfigRfGainReadLimitLo OBJECT-TYPE
        SYNTAX  INTEGER
        ACCESS  read-write
        STATUS  mandatory
        DESCRIPTION
            "The rf gain low warning limit in 0.1 dB units (in AGC ON mode)"
    ::={ epaConfigurationEntry 14 }

    epaConfigRfGainReadLimitHi OBJECT-TYPE
        SYNTAX  INTEGER
        ACCESS  read-write
        STATUS  mandatory
        DESCRIPTION
            "The rf gain high warning limit in 0.1 dB units (in AGC ON mode)"
    ::={ epaConfigurationEntry 15 }

    epaConfigRfGainReadLimitHiHi OBJECT-TYPE
        SYNTAX  INTEGER
        ACCESS  read-write
        STATUS  mandatory
        DESCRIPTION
            "The rf gain high alarm limit in 0.1 dB units (in AGC ON mode)"
    ::={ epaConfigurationEntry 16 }

-- *****
    epaConfigRfOutputLimitLoLo OBJECT-TYPE
        SYNTAX  INTEGER
        ACCESS  read-write
        STATUS  mandatory
        DESCRIPTION
            "The rf output low alarm limit in 0.1 dBm units"
    ::={ epaConfigurationEntry 17 }

    epaConfigRfOutputLimitLo OBJECT-TYPE
        SYNTAX  INTEGER
        ACCESS  read-write
        STATUS  mandatory
        DESCRIPTION
            "The rf output low warning limit in 0.1 dBm units"
    ::={ epaConfigurationEntry 18 }

    epaConfigRfOutputLimitHi OBJECT-TYPE
        SYNTAX  INTEGER
        ACCESS  read-write
        STATUS  mandatory
        DESCRIPTION
            "The rf output high warning limit in 0.1 dBm units"
    ::={ epaConfigurationEntry 19 }

    epaConfigRfOutputLimitHiHi OBJECT-TYPE
        SYNTAX  INTEGER
        ACCESS  read-write
        STATUS  mandatory
        DESCRIPTION
            "The rf output high alarm limit in 0.1 dBm units"
    ::={ epaConfigurationEntry 20 }


--*****************************************************************************************
-- Display group

    epaDisplayTable OBJECT-TYPE
        SYNTAX SEQUENCE OF EpaDisplayEntry
        ACCESS not-accessible
        STATUS mandatory
        DESCRIPTION ""
    ::= { epaDisplay 1 }

-- table of configuration entry(ro/rw)

    epaDisplayEntry OBJECT-TYPE
        SYNTAX EpaDisplayEntry
        ACCESS not-accessible
        STATUS mandatory
        DESCRIPTION ""
        INDEX { epaNESlot  }
    ::= { epaDisplayTable 1 }

-- the structure of the entry

    EpaDisplayEntry ::= SEQUENCE
    {
        epaDisplayRedundancySupported         TruthValue,
        epaDisplayDeviceRedundancyState       DeviceRedundancyState,
        epaDisplayDeviceActivity              DeviceActivityState
    }

    epaDisplayRedundancySupported OBJECT-TYPE
        SYNTAX  TruthValue
        ACCESS  read-only
        STATUS  mandatory
        DESCRIPTION "Returns true(1) if a the device supports redundancy"
    ::={ epaDisplayEntry 1 }

    epaDisplayDeviceRedundancyState OBJECT-TYPE
        SYNTAX  DeviceRedundancyState
        ACCESS  read-only
        STATUS  mandatory
        DESCRIPTION "Returns the device's redundancy state"
    ::={ epaDisplayEntry 2 }

    epaDisplayDeviceActivity OBJECT-TYPE
        SYNTAX  DeviceActivityState
        ACCESS  read-only
        STATUS  mandatory
        DESCRIPTION "Returns the actual device's activity state"
    ::={ epaDisplayEntry 3 }



END
