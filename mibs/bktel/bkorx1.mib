--- ****************************************************************************
-- *
-- * Description:   Implements definitions for the Orx1-modul
-- *                (Optical Receiver (BOR1000, SEO690, SEO691) design release V01)
-- *
-- * Copyright 2003 by BKtel communications GmbH
-- *
-- *
-- *     V.0.1 07.05.03  M. Heldmann    first draft
-- *     V.0.2 23.07.03  M. Heldmann    added descriptions for the states
-- *     V.0.3 07.01.04  M. Heldmann    added 'orx1ConfigOutputVoltageOffset'
-- *     V.0.4 06.04.04  M. Heldmann    changed description for 'orx1ConfigOutputVoltageOffset'
-- *     V.0.5 29.05.08  M. Heldmann    renamed threshold parameters in xxxxMeasuringValuesTable
-- *     V.0.6 11.07.13  M. Heldmann    adjusted syntax of "CommonEntry" to remove MIB compiler warnings
-- *     V.0.7 05.09.14  M. Heldmann    changed CommonModuleWidth and ConfigNESlotWrite STATUS to optional
-- ****************************************************************************

BKTEL-HFC862-ORX1-V01-MIB DEFINITIONS ::= BEGIN

    IMPORTS
        experimental, enterprises, TimeTicks, IpAddress, Counter
                 FROM RFC1155-SMI
    OBJECT-TYPE
                 FROM RFC-1212
        TRAP-TYPE
                 FROM RFC-1215
        modules, DisplayString, TruthValue, PerceivedSeverityValue, NESlotValue, ModuleWidthValue
                 FROM   BKTEL-HFC862-BASE-MIB
    ;

    orx1                 OBJECT IDENTIFIER ::= { modules 106 }
    orx1Common           OBJECT IDENTIFIER ::= { orx1 1 }
    orx1States           OBJECT IDENTIFIER ::= { orx1 2 }
    orx1Configuration    OBJECT IDENTIFIER ::= { orx1 3 }
    orx1Control          OBJECT IDENTIFIER ::= { orx1 4 }
    orx1MeasuringValues  OBJECT IDENTIFIER ::= { orx1 5 }
--  orx1Display          OBJECT IDENTIFIER ::= { orx1 6 }


--
-- Type definitions
--

    NESlotWriteValue ::= INTEGER (-1..99)


--*****************************************************************************************
-- ORX1 (Optical Receiver (BOR1000, SEO690, SEO691) design release V01)

--*****************************************************************************************
-- orx1Common group

    orx1CommonNumberOfModules OBJECT-TYPE
        SYNTAX  INTEGER(0..50)
        ACCESS  read-only
        STATUS  mandatory
        DESCRIPTION "Number of modules in table."
  ::= { orx1Common 1 }

    orx1CommonTable OBJECT-TYPE
        SYNTAX SEQUENCE OF Orx1CommonEntry
        ACCESS not-accessible
        STATUS mandatory
        DESCRIPTION "The table contains all modules of the ORX1-type in the NE"
  ::= { orx1Common 2 }

-- table of states entry(ro/rw)

    orx1CommonEntry OBJECT-TYPE
        SYNTAX Orx1CommonEntry
        ACCESS not-accessible
        STATUS mandatory
        DESCRIPTION "Common-Values for a module."
        INDEX { orx1NESlot }
  ::= { orx1CommonTable 1 }

-- the structure of the entry

    Orx1CommonEntry ::= SEQUENCE
    {
        orx1NESlot                      NESlotValue,
        orx1CommonType                  DisplayString,
        orx1CommonDescr                 DisplayString,
        orx1CommonFirmwareId            DisplayString,
        orx1CommonModuleWidth           ModuleWidthValue
    }

    orx1NESlot OBJECT-TYPE
        SYNTAX  NESlotValue
        ACCESS  read-only
        STATUS  mandatory
        DESCRIPTION
        "The slot number of the chassis for which this
        entry contains management information."
    ::= { orx1CommonEntry 1 }

    orx1CommonType OBJECT-TYPE
        SYNTAX  DisplayString  (SIZE(0..32))
        ACCESS  read-only
        STATUS  mandatory
        DESCRIPTION
        "The type of physical module. modSlotEmpty indicates
         an empty slot.  A Value of modSlotUnknown indicates
         that the type of module is unknown."
    ::= { orx1CommonEntry 2 }

    orx1CommonDescr OBJECT-TYPE
        SYNTAX  DisplayString
        ACCESS  read-write
        STATUS  mandatory
        DESCRIPTION
        "A textual description of the module.
        If not available, this Value should be
        set to a zero length string."
    ::= { orx1CommonEntry 3 }

    orx1CommonFirmwareId OBJECT-TYPE
        SYNTAX DisplayString (SIZE(0..32))
        ACCESS read-only
        STATUS mandatory
        DESCRIPTION "The firmware Id of the module."
    ::= { orx1CommonEntry 4 }

    orx1CommonModuleWidth OBJECT-TYPE
        SYNTAX ModuleWidthValue
        ACCESS read-only
        STATUS optional
        DESCRIPTION "The width of the module in multiples of slots (1, 2, ...)"
    ::= {  orx1CommonEntry 5  }

--*****************************************************************************************
-- orx1MeasuringValues group

-- table of measuring Values

    orx1MeasuringValuesTable OBJECT-TYPE
        SYNTAX SEQUENCE OF Orx1MeasuringValuesEntry
        ACCESS not-accessible
        STATUS mandatory
        DESCRIPTION ""
   ::= { orx1MeasuringValues 1 }

-- table of measuring Values entry

    orx1MeasuringValuesEntry OBJECT-TYPE
        SYNTAX Orx1MeasuringValuesEntry
        ACCESS not-accessible
        STATUS mandatory
        DESCRIPTION "Common-Values for a module."
        INDEX { orx1NESlot }
  ::= { orx1MeasuringValuesTable 1 }

--  the structure of the entry

    Orx1MeasuringValuesEntry ::= SEQUENCE
    {
        orx1InputPowerLoLo          INTEGER,
        orx1InputPowerLo            INTEGER,
        orx1InputPowerValue         INTEGER,
        orx1InputPowerHi            INTEGER,
        orx1InputPowerHiHi          INTEGER,

        orx1Plus24VLoLo             INTEGER,
        orx1Plus24VLo               INTEGER,
        orx1Plus24VValue            INTEGER,
        orx1Plus24VHi               INTEGER,
        orx1Plus24VHiHi             INTEGER,

        orx1TemperatureLoLo         INTEGER,
        orx1TemperatureLo           INTEGER,
        orx1TemperatureValue        INTEGER,
        orx1TemperatureHi           INTEGER,
        orx1TemperatureHiHi         INTEGER
    }

-- *****
    orx1InputPowerLoLo OBJECT-TYPE
        SYNTAX INTEGER
        ACCESS read-only
        STATUS mandatory
        DESCRIPTION "Input power low alarm threshold in steps of 0.1dBm."
    ::= { orx1MeasuringValuesEntry 1 }

    orx1InputPowerLo OBJECT-TYPE
        SYNTAX INTEGER
        ACCESS read-only
        STATUS mandatory
        DESCRIPTION "Input power low warning threshold in steps of 0.1dBm."
    ::= { orx1MeasuringValuesEntry 2 }

    orx1InputPowerValue OBJECT-TYPE
        SYNTAX INTEGER
        ACCESS read-only
        STATUS mandatory
        DESCRIPTION "Input power in steps of 0.1dBm."
    ::= { orx1MeasuringValuesEntry 3 }

    orx1InputPowerHi OBJECT-TYPE
        SYNTAX INTEGER
        ACCESS read-only
        STATUS mandatory
        DESCRIPTION "Input power high warning threshold in steps of 0.1dBm."
    ::= { orx1MeasuringValuesEntry 4 }

    orx1InputPowerHiHi OBJECT-TYPE
        SYNTAX INTEGER
        ACCESS read-only
        STATUS mandatory
        DESCRIPTION "Input power high alarm threshold in steps of 0.1dBm."
    ::= { orx1MeasuringValuesEntry 5 }

-- *****
    orx1Plus24VLoLo OBJECT-TYPE
        SYNTAX INTEGER
        ACCESS read-only
        STATUS mandatory
        DESCRIPTION "The +24V supply voltage low alarm threshold in steps of 0.1V."
    ::= { orx1MeasuringValuesEntry 6 }

    orx1Plus24VLo OBJECT-TYPE
        SYNTAX INTEGER
        ACCESS read-only
        STATUS mandatory
        DESCRIPTION "The +24V supply voltage low warning threshold in steps of 0.1V."
    ::= { orx1MeasuringValuesEntry 7 }

    orx1Plus24VValue OBJECT-TYPE
        SYNTAX INTEGER
        ACCESS read-only
        STATUS mandatory
        DESCRIPTION "The +24V supply voltage in steps of 0.1V."
    ::= { orx1MeasuringValuesEntry 8 }

    orx1Plus24VHi OBJECT-TYPE
        SYNTAX INTEGER
        ACCESS read-only
        STATUS mandatory
        DESCRIPTION "The +24V supply voltage high warning threshold in steps of 0.1V."
    ::= { orx1MeasuringValuesEntry 9 }

    orx1Plus24VHiHi OBJECT-TYPE
        SYNTAX INTEGER
        ACCESS read-only
        STATUS mandatory
        DESCRIPTION "The +24V supply voltage high alarm threshold in steps of 0.1V."
    ::= { orx1MeasuringValuesEntry 10 }

-- *****
    orx1TemperatureLoLo OBJECT-TYPE
        SYNTAX INTEGER
        ACCESS read-only
        STATUS mandatory
        DESCRIPTION "The module temperature low alarm threshold in steps of 0.1 celsius degrees."
    ::= { orx1MeasuringValuesEntry 11 }

    orx1TemperatureLo OBJECT-TYPE
        SYNTAX INTEGER
        ACCESS read-only
        STATUS mandatory
        DESCRIPTION "The module temperature low warning threshold in steps of 0.1 celsius degrees."
    ::= { orx1MeasuringValuesEntry 12 }

    orx1TemperatureValue OBJECT-TYPE
        SYNTAX INTEGER
        ACCESS read-only
        STATUS mandatory
        DESCRIPTION "The module temperature in steps of 0.1 celsius degrees."
    ::= { orx1MeasuringValuesEntry 13 }

    orx1TemperatureHi OBJECT-TYPE
        SYNTAX INTEGER
        ACCESS read-only
        STATUS mandatory
        DESCRIPTION "The module temperature high warning threshold in steps of 0.1 celsius degrees."
    ::= { orx1MeasuringValuesEntry 14 }

    orx1TemperatureHiHi OBJECT-TYPE
        SYNTAX INTEGER
        ACCESS read-only
        STATUS mandatory
        DESCRIPTION "The module temperature high alarm threshold in steps of 0.1 celsius degrees."
    ::= { orx1MeasuringValuesEntry 15 }


--*****************************************************************************************
--  orx1States group

-- Note: For every control OId there must be a correspondant alarm OId!

    orx1StatesTable OBJECT-TYPE
        SYNTAX SEQUENCE OF Orx1StatesEntry
        ACCESS not-accessible
        STATUS mandatory
        DESCRIPTION ""
    ::= { orx1States 1 }

-- table of states entry(ro/rw)

    orx1StatesEntry OBJECT-TYPE
        SYNTAX Orx1StatesEntry
        ACCESS not-accessible
        STATUS mandatory
        DESCRIPTION "Alarms for a module."
        INDEX { orx1NESlot }
    ::= { orx1StatesTable 1 }

-- the structure of the entry

    Orx1StatesEntry ::= SEQUENCE
    {
        orx1StatesInputLow       PerceivedSeverityValue,
        orx1StatesInputHigh      PerceivedSeverityValue,
        orx1StatesPlus24VLow     PerceivedSeverityValue,
        orx1StatesPlus24VHigh    PerceivedSeverityValue,
        orx1StatesBootloader     PerceivedSeverityValue,
        orx1StatesDefective      PerceivedSeverityValue
    }

    orx1StatesInputLow OBJECT-TYPE
        SYNTAX PerceivedSeverityValue
        ACCESS read-only
        STATUS mandatory
        DESCRIPTION "Optical input power low"
            -- Note: On input low alarm / orx1StatesInputLow == major(2)
            --  the receiver enters automatically into a power saving 
            --  sleep state
    ::= { orx1StatesEntry 1 }

    orx1StatesInputHigh OBJECT-TYPE
        SYNTAX PerceivedSeverityValue
        ACCESS read-only
        STATUS mandatory
        DESCRIPTION "Optical input power high"
    ::= { orx1StatesEntry 2 }

    orx1StatesPlus24VLow OBJECT-TYPE
        SYNTAX PerceivedSeverityValue
        ACCESS read-only
        STATUS mandatory
        DESCRIPTION "24 Volt supply low"
    ::= { orx1StatesEntry 3 }

    orx1StatesPlus24VHigh OBJECT-TYPE
        SYNTAX PerceivedSeverityValue
        ACCESS read-only
        STATUS mandatory
        DESCRIPTION "24 Volt supply high"
    ::= { orx1StatesEntry 4 }

    orx1StatesBootloader OBJECT-TYPE
        SYNTAX PerceivedSeverityValue
        ACCESS read-only
        STATUS mandatory
        DESCRIPTION 
            "The device is running in bootloader mode 
             without a legal application software." 
    ::= { orx1StatesEntry 5 }

    orx1StatesDefective OBJECT-TYPE
        SYNTAX PerceivedSeverityValue
        ACCESS read-only
        STATUS mandatory
        DESCRIPTION
            "The NEC has lost the connection to the device. 
             Reason may be a removed or defective device.
             Note that this state is set by the NEC and not 
             by the device" 
    ::= { orx1StatesEntry 6 }

--*****************************************************************************************
--  orx1Control group

  orx1ControlTable OBJECT-TYPE
    SYNTAX SEQUENCE OF Orx1ControlEntry
    ACCESS not-accessible
    STATUS mandatory
    DESCRIPTION ""
  ::= { orx1Control 1 }

-- table of control entry(ro/rw)

  orx1ControlEntry OBJECT-TYPE
    SYNTAX Orx1ControlEntry
    ACCESS not-accessible
    STATUS mandatory
    DESCRIPTION "Alarms for a module."
    INDEX { orx1NESlot }
  ::= { orx1ControlTable 1 }

-- the structure of the entry

    Orx1ControlEntry ::= SEQUENCE
    {
        orx1ControlReset             TruthValue,
        orx1ControlModuleLedBlink    TruthValue
    }

    orx1ControlReset OBJECT-TYPE
      SYNTAX TruthValue
      ACCESS read-write
      STATUS mandatory
      DESCRIPTION "Reset the module."
    ::= { orx1ControlEntry 1 }

    orx1ControlModuleLedBlink OBJECT-TYPE
        SYNTAX TruthValue
        ACCESS read-write
        STATUS mandatory
        DESCRIPTION   "Writing this variable to true(1) lets the device's 
        modul LED blink green for 10 seconds. 
        Writing this variable to false(2) storx1 blinking at once.
        This variable always returns false(2) on read requests"
    ::= { orx1ControlEntry 2 }


--*****************************************************************************************
-- orx1Configuration group

    orx1ConfigurationTable OBJECT-TYPE
        SYNTAX SEQUENCE OF Orx1ConfigurationEntry
        ACCESS not-accessible
        STATUS mandatory
        DESCRIPTION ""
    ::= { orx1Configuration 1 }

-- table of configuration entry(ro/rw)

    orx1ConfigurationEntry OBJECT-TYPE
        SYNTAX Orx1ConfigurationEntry
        ACCESS not-accessible
        STATUS mandatory
        DESCRIPTION ""
        INDEX { orx1NESlot  }
    ::= { orx1ConfigurationTable 1 }

-- the structure of the entry

    Orx1ConfigurationEntry ::= SEQUENCE
    {
        orx1ConfigNESlotWrite             NESlotWriteValue,
        orx1ConfigInputPwrLimitLoLo       INTEGER,
        orx1ConfigInputPwrLimitLo         INTEGER,
        orx1ConfigInputPwrLimitHi         INTEGER,
        orx1ConfigInputPwrLimitHiHi       INTEGER,
        orx1ConfigOutputVoltageOffset     INTEGER
    }

    orx1ConfigNESlotWrite OBJECT-TYPE
        SYNTAX NESlotWriteValue
        ACCESS read-write
        STATUS optional
        DESCRIPTION "By writing this variable a slot can be assigned
            for devices that dont support hardware slot detection.
            Reading '-1' means that the slot position is NOT writable."
    ::= { orx1ConfigurationEntry 1 }

    orx1ConfigInputPwrLimitLoLo OBJECT-TYPE
        SYNTAX  INTEGER
        ACCESS  read-write
        STATUS  mandatory
        DESCRIPTION
            "The optical input power low alarm limit in 0.1 dBm units"
    ::={ orx1ConfigurationEntry 2 }

    orx1ConfigInputPwrLimitLo OBJECT-TYPE
        SYNTAX  INTEGER
        ACCESS  read-write
        STATUS  mandatory
        DESCRIPTION
            "The optical input power low warning limit in 0.1 dBm units"
    ::={ orx1ConfigurationEntry 3 }

    orx1ConfigInputPwrLimitHi OBJECT-TYPE
        SYNTAX  INTEGER
        ACCESS  read-write
        STATUS  mandatory
        DESCRIPTION
            "The optical input power high warning limit in 0.1 dBm units"
    ::={ orx1ConfigurationEntry 4 }

    orx1ConfigInputPwrLimitHiHi OBJECT-TYPE
        SYNTAX  INTEGER
        ACCESS  read-write
        STATUS  mandatory
        DESCRIPTION
            "The optical input power high alarm limit in 0.1 dBm units"
    ::={ orx1ConfigurationEntry 5 }

    orx1ConfigOutputVoltageOffset OBJECT-TYPE
        SYNTAX  INTEGER
        ACCESS  read-write
        STATUS  mandatory
        DESCRIPTION
            "The offset from nominal output level voltage in 0.1 dB units"
    ::={ orx1ConfigurationEntry 6 }

--*****************************************************************************************
-- Display group




--*****************************************************************************************
END
