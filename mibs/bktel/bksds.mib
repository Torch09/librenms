-- *********************************************************************************************
-- *
-- * Description:   Implements definitions for all
-- *                Return Channel Stacking (BRCS) and Return Channel Destacking (BRCD) Modules
-- *
-- * Copyright 2006 by BKtel communications GmbH
-- *
-- *     V 0.1  04.04.2006  M. Heldmann  first draft
-- *     V.0.2  04.10.2006  M. Heldmann  NESlotWriteValue expanded due to new 2G6 platform needs
-- *     V.0.3  06.11.2006  M. Heldmann  renamed IngressMode
-- *     V.0.4  11.07.2013  M. Heldmann  adjusted syntax of "CommonEntry" to remove MIB compiler warnings
-- *     V.0.5  05.09.2014  M. Heldmann  changed CommonModuleWidth and ConfigNESlotWrite STATUS to optional
-- *********************************************************************************************

BKTEL-HFC862-STACKER-DESTACKER-MIB DEFINITIONS ::= BEGIN

    IMPORTS
        experimental, enterprises, TimeTicks, IpAddress, Counter
                 FROM RFC1155-SMI
    OBJECT-TYPE
                 FROM RFC-1212
        TRAP-TYPE
                 FROM RFC-1215
        modules, DisplayString, TruthValue, PerceivedSeverityValue, NESlotValue, ModuleWidthValue
                 FROM   BKTEL-HFC862-BASE-MIB
    ;

    sds                  OBJECT IDENTIFIER ::= { modules 112 }
    sdsCommon            OBJECT IDENTIFIER ::= { sds 1 }
    sdsStates            OBJECT IDENTIFIER ::= { sds 2 }
    sdsConfiguration     OBJECT IDENTIFIER ::= { sds 3 }
    sdsControl           OBJECT IDENTIFIER ::= { sds 4 }
    sdsMeasuringValues   OBJECT IDENTIFIER ::= { sds 5 }
    sdsDisplay           OBJECT IDENTIFIER ::= { sds 6 }


--
-- Type definitions
--

    ModuleType ::= INTEGER
        {
        stacker(1),
        destacker(2)
        }

    ModuleSubtype ::= INTEGER
        {
        baseModule(1),
        expansionModule(2)
        }

    ServicePilotMode ::= INTEGER
        {
        servicePilotOff(1),
        servicePilotOn(2)
        }

    IngressMode ::= INTEGER
        {
        noAttenuator(1),
        attenuator_6dB(2),
        attenuator_40dB(3)
        }

    NESlotWriteValue ::= INTEGER (-1..99)


-- sdsCommon group

    sdsCommonNumberOfModules OBJECT-TYPE
        SYNTAX  INTEGER(0..50)
        ACCESS  read-only
        STATUS  mandatory
        DESCRIPTION "Number of modules in table."
    ::= { sdsCommon 1 }

    sdsCommonTable OBJECT-TYPE
        SYNTAX SEQUENCE OF SdsCommonEntry
        ACCESS not-accessible
        STATUS mandatory
        DESCRIPTION "The table contains all modules of the Stacker-Destacker type in the NE"
    ::= { sdsCommon 2 }

-- table of states entry(ro/rw)

    sdsCommonEntry OBJECT-TYPE
        SYNTAX SdsCommonEntry
        ACCESS not-accessible
        STATUS mandatory
        DESCRIPTION "Common-Values for a module."
        INDEX { sdsNESlot }
    ::= { sdsCommonTable 1 }

-- the structure of the entry

    SdsCommonEntry ::= SEQUENCE
    {
        sdsNESlot                      NESlotValue,
        sdsCommonType                  DisplayString,
        sdsCommonDescr                 DisplayString,
        sdsCommonFirmwareId            DisplayString,
        sdsCommonModuleWidth           ModuleWidthValue
    }

    sdsNESlot OBJECT-TYPE
        SYNTAX  NESlotValue
        ACCESS  read-only
        STATUS  mandatory
        DESCRIPTION
        "The slot number of the chassis for which this
        entry contains management information."
    ::= { sdsCommonEntry 1 }

    sdsCommonType OBJECT-TYPE
        SYNTAX  DisplayString  (SIZE(0..32))
        ACCESS  read-only
        STATUS  mandatory
        DESCRIPTION
        "The type of the module"
    ::= { sdsCommonEntry 2 }

    sdsCommonDescr OBJECT-TYPE
        SYNTAX  DisplayString
        ACCESS  read-write
        STATUS  mandatory
        DESCRIPTION
        "A textual description of the module"
    ::= { sdsCommonEntry 3 }

    sdsCommonFirmwareId OBJECT-TYPE
        SYNTAX DisplayString (SIZE(0..32))
        ACCESS read-only
        STATUS mandatory
        DESCRIPTION "The firmware release of the module, for example 'Release 1.2 / 12 May 05'"
    ::= { sdsCommonEntry 4 }

    sdsCommonModuleWidth OBJECT-TYPE
        SYNTAX ModuleWidthValue
        ACCESS read-only
        STATUS optional
        DESCRIPTION 
        "The width of the module in multiples of slots (1, 2, ...)
        Returns 0 for special housings (for example 19inch, etc...)"
    ::= { sdsCommonEntry 5 }


--*****************************************************************************************
-- sdsMeasuringValues group

-- table of measuring Values

    sdsMeasuringValuesTable OBJECT-TYPE
        SYNTAX SEQUENCE OF SdsMeasuringValuesEntry
        ACCESS not-accessible
        STATUS mandatory
        DESCRIPTION ""
    ::= { sdsMeasuringValues 1 }

-- table of measuring Values entry

    sdsMeasuringValuesEntry OBJECT-TYPE
        SYNTAX SdsMeasuringValuesEntry
        ACCESS not-accessible
        STATUS mandatory
        DESCRIPTION "Common-Values for a module."
        INDEX { sdsNESlot }
    ::= { sdsMeasuringValuesTable 1 }

--  the structure of the entry

    SdsMeasuringValuesEntry ::= SEQUENCE
    {
        sdsTemperatureLoLo      INTEGER,
        sdsTemperatureLo        INTEGER,
        sdsTemperatureValue     INTEGER,
        sdsTemperatureHi        INTEGER,
        sdsTemperatureHiHi      INTEGER
    }

-- *****
    sdsTemperatureLoLo OBJECT-TYPE
        SYNTAX INTEGER
        ACCESS read-only
        STATUS mandatory
        DESCRIPTION "Device temperature low alarm threshold in 0.1 celsius degrees."
    ::= { sdsMeasuringValuesEntry 1 }

    sdsTemperatureLo OBJECT-TYPE
        SYNTAX INTEGER
        ACCESS read-only
        STATUS mandatory
        DESCRIPTION "Device temperature low warning threshold in 0.1 celsius degrees."
    ::= { sdsMeasuringValuesEntry 2 }

    sdsTemperatureValue OBJECT-TYPE
        SYNTAX INTEGER
        ACCESS read-only
        STATUS mandatory
        DESCRIPTION "Device temperature in 0.1 celsius degrees."
    ::= { sdsMeasuringValuesEntry 3 }

    sdsTemperatureHi OBJECT-TYPE
        SYNTAX INTEGER
        ACCESS read-only
        STATUS mandatory
        DESCRIPTION "Device temperature high warning threshold in 0.1 celsius degrees."
    ::= { sdsMeasuringValuesEntry 4 }

    sdsTemperatureHiHi OBJECT-TYPE
        SYNTAX INTEGER
        ACCESS read-only
        STATUS mandatory
        DESCRIPTION "Device temperature high alarm threshold in 0.1 celsius degrees."
    ::= { sdsMeasuringValuesEntry 5 }


--*****************************************************************************************
--  sdsStates group

    sdsStatesTable OBJECT-TYPE
        SYNTAX SEQUENCE OF SdsStatesEntry
        ACCESS not-accessible
        STATUS mandatory
        DESCRIPTION ""
    ::= { sdsStates 1 }

-- table of states entry(ro/rw)

    sdsStatesEntry OBJECT-TYPE
        SYNTAX SdsStatesEntry
        ACCESS not-accessible
        STATUS mandatory
        DESCRIPTION "Alarms for a module."
        INDEX { sdsNESlot }
    ::= { sdsStatesTable 1 }

-- the structure of the entry

    SdsStatesEntry ::= SEQUENCE
    {
        sdsStatesBootloader          PerceivedSeverityValue,
        sdsStatesCommLoss            PerceivedSeverityValue,
        sdsStatesTemperatureLow      PerceivedSeverityValue,
        sdsStatesTemperatureHigh     PerceivedSeverityValue,
        sdsStatesModulatedChannel    PerceivedSeverityValue,
        sdsStatesBasebandChannel     PerceivedSeverityValue,
        sdsStatesServicePilotActive  PerceivedSeverityValue,
        sdsStatesLocalOscLockedState PerceivedSeverityValue
    }

    sdsStatesBootloader OBJECT-TYPE
        SYNTAX PerceivedSeverityValue
        ACCESS read-only
        STATUS mandatory
        DESCRIPTION
            "The device is running in bootloader mode
             without a legal application software."
    ::= { sdsStatesEntry 1 }

    sdsStatesCommLoss OBJECT-TYPE
        SYNTAX PerceivedSeverityValue
        ACCESS read-only
        STATUS mandatory
        DESCRIPTION
            "The NEC has lost the connection to the device.
             Reason may be a removed or defective device.
             Note that this state is set by the NEC and not
             by the device"
    ::= { sdsStatesEntry 2 }

    sdsStatesTemperatureLow OBJECT-TYPE
        SYNTAX PerceivedSeverityValue
        ACCESS read-only
        STATUS mandatory
        DESCRIPTION "Device temperature low"
    ::= { sdsStatesEntry 3 }

    sdsStatesTemperatureHigh OBJECT-TYPE
        SYNTAX PerceivedSeverityValue
        ACCESS read-only
        STATUS mandatory
        DESCRIPTION "Device temperature high"
    ::= { sdsStatesEntry 4 }

    sdsStatesModulatedChannel OBJECT-TYPE
        SYNTAX PerceivedSeverityValue
        ACCESS read-only
        STATUS mandatory
        DESCRIPTION "Device internal modulated channel circuit failure"
    ::= { sdsStatesEntry 5 }

    sdsStatesBasebandChannel OBJECT-TYPE
        SYNTAX PerceivedSeverityValue
        ACCESS read-only
        STATUS mandatory
        DESCRIPTION "Device internal baseband channel circuit failure"
    ::= { sdsStatesEntry 6 }

    sdsStatesServicePilotActive OBJECT-TYPE
        SYNTAX PerceivedSeverityValue
        ACCESS read-only
        STATUS mandatory
        DESCRIPTION "Service pilot active"
    ::= { sdsStatesEntry 7 }

    sdsStatesLocalOscLockedState OBJECT-TYPE
        SYNTAX PerceivedSeverityValue
        ACCESS read-only
        STATUS mandatory
        DESCRIPTION "Local oscillator not locked"
    ::= { sdsStatesEntry 8 }


--*****************************************************************************************
--  sdsControl group

    sdsControlTable OBJECT-TYPE
        SYNTAX SEQUENCE OF SdsControlEntry
        ACCESS not-accessible
        STATUS mandatory
        DESCRIPTION ""
    ::= { sdsControl 1 }

-- table of control entry(ro/rw)

    sdsControlEntry OBJECT-TYPE
        SYNTAX SdsControlEntry
        ACCESS not-accessible
        STATUS mandatory
        DESCRIPTION "Alarms for a module."
        INDEX { sdsNESlot }
    ::= { sdsControlTable 1 }

-- the structure of the entry

    SdsControlEntry ::= SEQUENCE
    {
        sdsControlReset            TruthValue,
        sdsControlModuleLedBlink   TruthValue,
        sdsControlServicePilot     ServicePilotMode
    }

    sdsControlReset OBJECT-TYPE
      SYNTAX TruthValue
      ACCESS read-write
      STATUS mandatory
      DESCRIPTION "Reset the module."
    ::= { sdsControlEntry 1 }

    sdsControlModuleLedBlink OBJECT-TYPE
        SYNTAX TruthValue
        ACCESS read-write
        STATUS mandatory
        DESCRIPTION "Writing this variable to true(1) lets the device's
        modul LED blink green for 10 seconds.
        Writing this variable to false(2) stops blinking at once.
        This variable always returns false(2) on read requests"
    ::= { sdsControlEntry 2 }

    sdsControlServicePilot OBJECT-TYPE
      SYNTAX ServicePilotMode
      ACCESS read-write
      STATUS mandatory
      DESCRIPTION "Switches the service pilot signal ON and OFF.
            Only valid for 'stacker' modules, i.e.: 
             sdsDisplayModuleType == stacker(1)"
    ::= { sdsControlEntry 3 }


--*****************************************************************************************
-- sdsConfiguration group

    sdsConfigurationTable OBJECT-TYPE
        SYNTAX SEQUENCE OF SdsConfigurationEntry
        ACCESS not-accessible
        STATUS mandatory
        DESCRIPTION ""
    ::= { sdsConfiguration 1 }

-- table of configuration entry(ro/rw)

    sdsConfigurationEntry OBJECT-TYPE
        SYNTAX SdsConfigurationEntry
        ACCESS not-accessible
        STATUS mandatory
        DESCRIPTION ""
        INDEX { sdsNESlot  }
    ::= { sdsConfigurationTable 1 }

-- the structure of the entry

    SdsConfigurationEntry ::= SEQUENCE
    {
        sdsConfigNESlotWrite             NESlotWriteValue,
        sdsConfigGainModulatedChannel    INTEGER,
        sdsConfigGainBasebandChannel     INTEGER,
        sdsConfigGainCommon              INTEGER,
        sdsConfigIngressModulatedChannel IngressMode,
        sdsConfigIngressBasebandChannel  IngressMode
    }

    sdsConfigNESlotWrite OBJECT-TYPE
        SYNTAX NESlotWriteValue
        ACCESS read-write
        STATUS optional
        DESCRIPTION "By writing this variable a slot can be assigned
            for devices that dont support hardware slot detection.
            Reading '-1' means that the slot position is NOT writable."
   ::= { sdsConfigurationEntry 1 }

    sdsConfigGainModulatedChannel OBJECT-TYPE
        SYNTAX INTEGER
        ACCESS read-write
        STATUS mandatory
        DESCRIPTION "Gain of module's modulated channel in 0.1 dB units"
    ::= { sdsConfigurationEntry 2 }

    sdsConfigGainBasebandChannel OBJECT-TYPE
        SYNTAX INTEGER
        ACCESS read-write
        STATUS mandatory
        DESCRIPTION "Gain of module's baseband channel in 0.1 dB units
            Only valid for 'base' modules, i.e.: 
             sdsDisplayModuleSubtype == baseModule(1)
            Always returns 0dB if not valid"
    ::= { sdsConfigurationEntry 3 }

    sdsConfigGainCommon OBJECT-TYPE
        SYNTAX INTEGER
        ACCESS read-write
        STATUS mandatory
        DESCRIPTION "Gain common for baseband and modulated channels in 0.1 dB units
            Only valid for 'stacker-base' modules, i.e.: 
             sdsDisplayModuleType == stacker(1)
                AND
             sdsDisplayModuleSubtype == baseModule(1)
            Always returns 0dB if not valid"
    ::= { sdsConfigurationEntry 4 }

    sdsConfigIngressModulatedChannel OBJECT-TYPE
      SYNTAX IngressMode
      ACCESS read-write
      STATUS mandatory
      DESCRIPTION "The ingresse mode.
            Only valid for 'stacker' modules, i.e.: 
             sdsDisplayModuleType == stacker(1)"
    ::= { sdsConfigurationEntry 5 }

    sdsConfigIngressBasebandChannel OBJECT-TYPE
      SYNTAX IngressMode
      ACCESS read-write
      STATUS mandatory
      DESCRIPTION "The ingresse mode.
            Only valid for 'stacker-base' modules, i.e.: 
             sdsDisplayModuleType == stacker(1)
                AND
             sdsDisplayModuleSubtype == baseModule(1)
            Always returns 0dB if not valid"
    ::= { sdsConfigurationEntry 6 }


--*****************************************************************************************
-- Display group

    sdsDisplayTable OBJECT-TYPE
        SYNTAX SEQUENCE OF SdsDisplayEntry
        ACCESS not-accessible
        STATUS mandatory
        DESCRIPTION ""
    ::= { sdsDisplay 1 }

-- table of display entry

    sdsDisplayEntry OBJECT-TYPE
        SYNTAX SdsDisplayEntry
        ACCESS not-accessible
        STATUS mandatory
        DESCRIPTION ""
        INDEX { sdsNESlot  }
    ::= { sdsDisplayTable 1 }

-- the structure of the entry

    SdsDisplayEntry ::= SEQUENCE
    {
        sdsDisplayModuleType           ModuleType,
        sdsDisplayModuleSubtype        ModuleSubtype,
        sdsDisplayModulationFrequency  INTEGER
    }

    sdsDisplayModuleType OBJECT-TYPE
        SYNTAX ModuleType
        ACCESS read-only
        STATUS mandatory
        DESCRIPTION "The module type"
    ::= { sdsDisplayEntry 1 }

    sdsDisplayModuleSubtype OBJECT-TYPE
        SYNTAX ModuleSubtype
        ACCESS read-only
        STATUS mandatory
        DESCRIPTION "The module subtype"
    ::= { sdsDisplayEntry 2 }

    sdsDisplayModulationFrequency OBJECT-TYPE
        SYNTAX INTEGER
        ACCESS read-only
        STATUS mandatory
        DESCRIPTION "Used modulation frequency of modulated channel in 0.01 kHz units"
    ::= { sdsDisplayEntry 3 }


END
