--- ****************************************************************************
-- *
-- * Description:   Implements definitions for the Wisi CD24-modul
-- *
-- * Copyright 2003 by BKtel communications GmbH
-- *
-- *     V.0.1 11.11.03  M. Heldmann    first draft
-- *     V.0.2 25.02.04  J. Anhorn 		units changed for cd24ConfigOutputCurrentLimitxx
-- *     V.0.3 04.10.06  M. Heldmann    NESlotWriteValue expanded due to new 2G6 platform needs
-- *     V.0.4 29.05.08  M. Heldmann    renamed threshold parameters in xxxxMeasuringValuesTable
-- *     V.0.5 11.07.13  M. Heldmann    adjusted syntax of "CommonEntry" to remove MIB compiler warnings
-- ****************************************************************************

BKTEL-HFC862-WISI-CD24-MIB DEFINITIONS ::= BEGIN

    IMPORTS
        experimental, enterprises, TimeTicks, IpAddress, Counter
                 FROM RFC1155-SMI
    OBJECT-TYPE
                 FROM RFC-1212
        TRAP-TYPE
                 FROM RFC-1215
        modules, DisplayString, TruthValue, PerceivedSeverityValue, NESlotValue, ModuleWidthValue
                 FROM   BKTEL-HFC862-BASE-MIB
    ;

    cd24                 OBJECT IDENTIFIER ::= { modules 301 }
    cd24Common           OBJECT IDENTIFIER ::= { cd24 1 }
    cd24States           OBJECT IDENTIFIER ::= { cd24 2 }
    cd24Configuration    OBJECT IDENTIFIER ::= { cd24 3 }
    cd24Control          OBJECT IDENTIFIER ::= { cd24 4 }
    cd24MeasuringValues  OBJECT IDENTIFIER ::= { cd24 5 }


--
-- Type definitions
--

    NESlotWriteValue ::= INTEGER (-1..99)


--*****************************************************************************************
-- CD24 (Wisi Power Supply)

--*****************************************************************************************
-- cd24Common group

    cd24CommonNumberOfModules OBJECT-TYPE
        SYNTAX  INTEGER(0..50)
        ACCESS  read-only
        STATUS  mandatory
        DESCRIPTION "Number of modules in table."
  ::= { cd24Common 1 }

    cd24CommonTable OBJECT-TYPE
        SYNTAX SEQUENCE OF Cd24CommonEntry
        ACCESS not-accessible
        STATUS mandatory
        DESCRIPTION "The table contains all modules of the CD24-type in the NE"
  ::= { cd24Common 2 }

-- table of states entry(ro/rw)

    cd24CommonEntry OBJECT-TYPE
        SYNTAX Cd24CommonEntry
        ACCESS not-accessible
        STATUS mandatory
        DESCRIPTION "Common-Values for a module."
        INDEX { cd24NESlot }
  ::= { cd24CommonTable 1 }

-- the structure of the entry

    Cd24CommonEntry ::= SEQUENCE
    {
        cd24NESlot                      NESlotValue,
        cd24CommonType                  DisplayString,
        cd24CommonDescr                 DisplayString,
        cd24CommonFirmwareId            DisplayString,
        cd24CommonModuleWidth           ModuleWidthValue
    }

    cd24NESlot OBJECT-TYPE
        SYNTAX  NESlotValue
        ACCESS  read-only
        STATUS  mandatory
        DESCRIPTION
        "The slot number of the chassis for which this
        entry contains management information."
    ::= { cd24CommonEntry 1 }

    cd24CommonType OBJECT-TYPE
        SYNTAX  DisplayString  (SIZE(0..32))
        ACCESS  read-only
        STATUS  mandatory
        DESCRIPTION
        "The type of physical module. modSlotEmpty indicates
         an empty slot.  A Value of modSlotUnknown indicates
         that the type of module is unknown."
    ::= { cd24CommonEntry 2 }

    cd24CommonDescr OBJECT-TYPE
        SYNTAX  DisplayString
        ACCESS  read-write
        STATUS  mandatory
        DESCRIPTION
        "A textual description of the module.
        If not available, this Value should be
        set to a zero length string."
    ::= { cd24CommonEntry 3 }

    cd24CommonFirmwareId OBJECT-TYPE
        SYNTAX DisplayString (SIZE(0..32))
        ACCESS read-only
        STATUS mandatory
        DESCRIPTION "The firmware Id of the module."
    ::= { cd24CommonEntry 4 }

    cd24CommonModuleWidth OBJECT-TYPE
        SYNTAX ModuleWidthValue
        ACCESS read-only
        STATUS mandatory
        DESCRIPTION "The width of the module in multiples of slots (1, 2, ...)"
    ::= { cd24CommonEntry 5 }

--*****************************************************************************************
-- cd24MeasuringValues group

-- table of measuring Values

    cd24MeasuringValuesTable OBJECT-TYPE
        SYNTAX SEQUENCE OF Cd24MeasuringValuesEntry
        ACCESS not-accessible
        STATUS mandatory
        DESCRIPTION ""
   ::= { cd24MeasuringValues 1 }

-- table of measuring Values entry

    cd24MeasuringValuesEntry OBJECT-TYPE
        SYNTAX Cd24MeasuringValuesEntry
        ACCESS not-accessible
        STATUS mandatory
        DESCRIPTION "Common-Values for a module."
        INDEX { cd24NESlot }
  ::= { cd24MeasuringValuesTable 1 }

--  the structure of the entry

    Cd24MeasuringValuesEntry ::= SEQUENCE
    {
        cd24InputVoltageLoLo          INTEGER,
        cd24InputVoltageLo            INTEGER,
        cd24InputVoltageValue         INTEGER,
        cd24InputVoltageHi            INTEGER,
        cd24InputVoltageHiHi          INTEGER,

        cd24Plus24VLoLo               INTEGER,
        cd24Plus24VLo                 INTEGER,
        cd24Plus24VValue              INTEGER,
        cd24Plus24VHi                 INTEGER,
        cd24Plus24VHiHi               INTEGER,

        cd24Plus7p5VLoLo              INTEGER,
        cd24Plus7p5VLo                INTEGER,
        cd24Plus7p5VValue             INTEGER,
        cd24Plus7p5VHi                INTEGER,
        cd24Plus7p5VHiHi              INTEGER,

        cd24OutputCurrentLoLo         INTEGER,
        cd24OutputCurrentLo           INTEGER,
        cd24OutputCurrentValue        INTEGER,
        cd24OutputCurrentHi           INTEGER,
        cd24OutputCurrentHiHi         INTEGER
    }

-- *****
    cd24InputVoltageLoLo OBJECT-TYPE
        SYNTAX INTEGER
        ACCESS read-only
        STATUS mandatory
        DESCRIPTION "Input voltage low alarm threshold in steps of 0.1V"
    ::= { cd24MeasuringValuesEntry 1 }

    cd24InputVoltageLo OBJECT-TYPE
        SYNTAX INTEGER
        ACCESS read-only
        STATUS mandatory
        DESCRIPTION "Input voltage low warning threshold in steps of 0.1V"
    ::= { cd24MeasuringValuesEntry 2 }

    cd24InputVoltageValue OBJECT-TYPE
        SYNTAX INTEGER
        ACCESS read-only
        STATUS mandatory
        DESCRIPTION "Input voltage in steps of 0.1V"
    ::= { cd24MeasuringValuesEntry 3 }

    cd24InputVoltageHi OBJECT-TYPE
        SYNTAX INTEGER
        ACCESS read-only
        STATUS mandatory
        DESCRIPTION "Input voltage high warning threshold in steps of 0.1V"
    ::= { cd24MeasuringValuesEntry 4 }

    cd24InputVoltageHiHi OBJECT-TYPE
        SYNTAX INTEGER
        ACCESS read-only
        STATUS mandatory
        DESCRIPTION "Input voltage high alarm threshold in steps of 0.1V"
    ::= { cd24MeasuringValuesEntry 5 }

-- *****
    cd24Plus24VLoLo OBJECT-TYPE
        SYNTAX INTEGER
        ACCESS read-only
        STATUS mandatory
        DESCRIPTION "+24V output voltage low alarm threshold in steps of 0.1V"
    ::= { cd24MeasuringValuesEntry 6 }

    cd24Plus24VLo OBJECT-TYPE
        SYNTAX INTEGER
        ACCESS read-only
        STATUS mandatory
        DESCRIPTION "+24V output voltage low warning threshold in steps of 0.1V"
    ::= { cd24MeasuringValuesEntry 7 }

    cd24Plus24VValue OBJECT-TYPE
        SYNTAX INTEGER
        ACCESS read-only
        STATUS mandatory
        DESCRIPTION "+24V output voltage in steps of 0.1V"
    ::= { cd24MeasuringValuesEntry 8 }

    cd24Plus24VHi OBJECT-TYPE
        SYNTAX INTEGER
        ACCESS read-only
        STATUS mandatory
        DESCRIPTION "+24V output voltage high warning threshold in steps of 0.1V"
    ::= { cd24MeasuringValuesEntry 9 }

    cd24Plus24VHiHi OBJECT-TYPE
        SYNTAX INTEGER
        ACCESS read-only
        STATUS mandatory
        DESCRIPTION "+24V output voltage high alarm threshold in steps of 0.1V"
    ::= { cd24MeasuringValuesEntry 10 }

-- *****
    cd24Plus7p5VLoLo OBJECT-TYPE
        SYNTAX INTEGER
        ACCESS read-only
        STATUS mandatory
        DESCRIPTION "+7.5V output voltage low alarm threshold in steps of 0.1V"
    ::= { cd24MeasuringValuesEntry 11 }

    cd24Plus7p5VLo OBJECT-TYPE
        SYNTAX INTEGER
        ACCESS read-only
        STATUS mandatory
        DESCRIPTION "+7.5V output voltage low warning threshold in steps of 0.1V"
    ::= { cd24MeasuringValuesEntry 12 }

    cd24Plus7p5VValue OBJECT-TYPE
        SYNTAX INTEGER
        ACCESS read-only
        STATUS mandatory
        DESCRIPTION "+7.5V output voltage in steps of 0.1V"
    ::= { cd24MeasuringValuesEntry 13 }

    cd24Plus7p5VHi OBJECT-TYPE
        SYNTAX INTEGER
        ACCESS read-only
        STATUS mandatory
        DESCRIPTION "+7.5V output voltage high warning threshold in steps of 0.1V"
    ::= { cd24MeasuringValuesEntry 14 }

    cd24Plus7p5VHiHi OBJECT-TYPE
        SYNTAX INTEGER
        ACCESS read-only
        STATUS mandatory
        DESCRIPTION "+7.5V output voltage high alarm threshold in steps of 0.1V"
    ::= { cd24MeasuringValuesEntry 15 }

-- *****
    cd24OutputCurrentLoLo OBJECT-TYPE
        SYNTAX INTEGER
        ACCESS read-only
        STATUS mandatory
        DESCRIPTION "Output current low alarm threshold in steps of 1 mA"
    ::= { cd24MeasuringValuesEntry 16 }

    cd24OutputCurrentLo OBJECT-TYPE
        SYNTAX INTEGER
        ACCESS read-only
        STATUS mandatory
        DESCRIPTION "Output current low warning threshold in steps of 1 mA"
    ::= { cd24MeasuringValuesEntry 17 }

    cd24OutputCurrentValue OBJECT-TYPE
        SYNTAX INTEGER
        ACCESS read-only
        STATUS mandatory
        DESCRIPTION "Output current in steps of 1 mA"
    ::= { cd24MeasuringValuesEntry 18 }

    cd24OutputCurrentHi OBJECT-TYPE
        SYNTAX INTEGER
        ACCESS read-only
        STATUS mandatory
        DESCRIPTION "Output current high warning threshold in steps of 1 mA"
    ::= { cd24MeasuringValuesEntry 19 }

    cd24OutputCurrentHiHi OBJECT-TYPE
        SYNTAX INTEGER
        ACCESS read-only
        STATUS mandatory
        DESCRIPTION "Output current high alarm threshold in steps of 1 mA"
    ::= { cd24MeasuringValuesEntry 20 }


--*****************************************************************************************
--  cd24States group

-- Note: For every control OId there must be a correspondant alarm OId!

    cd24StatesTable OBJECT-TYPE
        SYNTAX SEQUENCE OF Cd24StatesEntry
        ACCESS not-accessible
        STATUS mandatory
        DESCRIPTION ""
    ::= { cd24States 1 }

-- table of states entry(ro/rw)

    cd24StatesEntry OBJECT-TYPE
        SYNTAX Cd24StatesEntry
        ACCESS not-accessible
        STATUS mandatory
        DESCRIPTION "Alarms for a module."
        INDEX { cd24NESlot }
    ::= { cd24StatesTable 1 }

-- the structure of the entry

    Cd24StatesEntry ::= SEQUENCE
    {
        cd24StatesInputVoltageLow       PerceivedSeverityValue,
        cd24StatesInputVoltageHigh      PerceivedSeverityValue,
        cd24StatesPlus24VLow            PerceivedSeverityValue,
        cd24StatesPlus24VHigh           PerceivedSeverityValue,
        cd24StatesPlus7p5VLow           PerceivedSeverityValue,
        cd24StatesPlus7p5VHigh          PerceivedSeverityValue,
        cd24StatesOutputCurrentLow      PerceivedSeverityValue,
        cd24StatesOutputCurrentHigh     PerceivedSeverityValue,
        cd24StatesDefective             PerceivedSeverityValue
    }

    cd24StatesInputVoltageLow OBJECT-TYPE
        SYNTAX PerceivedSeverityValue
        ACCESS read-only
        STATUS mandatory
        DESCRIPTION "Input voltage low"
    ::= { cd24StatesEntry 1 }

    cd24StatesInputVoltageHigh OBJECT-TYPE
        SYNTAX PerceivedSeverityValue
        ACCESS read-only
        STATUS mandatory
        DESCRIPTION "Input voltage high"
    ::= { cd24StatesEntry 2 }

    cd24StatesPlus24VLow OBJECT-TYPE
        SYNTAX PerceivedSeverityValue
        ACCESS read-only
        STATUS mandatory
        DESCRIPTION "24 Volt output voltage low"
    ::= { cd24StatesEntry 3 }

    cd24StatesPlus24VHigh OBJECT-TYPE
        SYNTAX PerceivedSeverityValue
        ACCESS read-only
        STATUS mandatory
        DESCRIPTION "24 Volt output voltage high"
    ::= { cd24StatesEntry 4 }

    cd24StatesPlus7p5VLow OBJECT-TYPE
        SYNTAX PerceivedSeverityValue
        ACCESS read-only
        STATUS mandatory
        DESCRIPTION "7.5 Volt output voltage low"
    ::= { cd24StatesEntry 5 }

    cd24StatesPlus7p5VHigh OBJECT-TYPE
        SYNTAX PerceivedSeverityValue
        ACCESS read-only
        STATUS mandatory
        DESCRIPTION "7.5 Volt output voltage high"
    ::= { cd24StatesEntry 6 }

    cd24StatesOutputCurrentLow OBJECT-TYPE
        SYNTAX PerceivedSeverityValue
        ACCESS read-only
        STATUS mandatory
        DESCRIPTION "Output current low"
    ::= { cd24StatesEntry 7 }

    cd24StatesOutputCurrentHigh OBJECT-TYPE
        SYNTAX PerceivedSeverityValue
        ACCESS read-only
        STATUS mandatory
        DESCRIPTION "Output current high"
    ::= { cd24StatesEntry 8 }

    cd24StatesDefective OBJECT-TYPE
        SYNTAX PerceivedSeverityValue
        ACCESS read-only
        STATUS mandatory
        DESCRIPTION
            "The NEC has lost the connection to the device. 
             Reason may be a removed or defective device.
             Note that this state is set by the NEC and not 
             by the device" 
    ::= { cd24StatesEntry 9 }

--*****************************************************************************************
--  cd24Control group

  cd24ControlTable OBJECT-TYPE
    SYNTAX SEQUENCE OF Cd24ControlEntry
    ACCESS not-accessible
    STATUS mandatory
    DESCRIPTION ""
  ::= { cd24Control 1 }

-- table of control entry(ro/rw)

  cd24ControlEntry OBJECT-TYPE
    SYNTAX Cd24ControlEntry
    ACCESS not-accessible
    STATUS mandatory
    DESCRIPTION "Alarms for a module."
    INDEX { cd24NESlot }
  ::= { cd24ControlTable 1 }

-- the structure of the entry

    Cd24ControlEntry ::= SEQUENCE
    {
        cd24ControlReset  TruthValue
    }

    cd24ControlReset OBJECT-TYPE
      SYNTAX TruthValue
      ACCESS read-write
      STATUS mandatory
      DESCRIPTION "Reset the module."
    ::= { cd24ControlEntry 1 }


--*****************************************************************************************
-- cd24Configuration group

    cd24ConfigurationTable OBJECT-TYPE
        SYNTAX SEQUENCE OF Cd24ConfigurationEntry
        ACCESS not-accessible
        STATUS mandatory
        DESCRIPTION ""
    ::= { cd24Configuration 1 }

-- table of configuration entry(ro/rw)

    cd24ConfigurationEntry OBJECT-TYPE
        SYNTAX Cd24ConfigurationEntry
        ACCESS not-accessible
        STATUS mandatory
        DESCRIPTION ""
        INDEX { cd24NESlot  }
    ::= { cd24ConfigurationTable 1 }

-- the structure of the entry

    Cd24ConfigurationEntry ::= SEQUENCE
    {
        cd24ConfigNESlotWrite                 NESlotWriteValue,
        cd24ConfigInputVoltageLimitLoLo       INTEGER,
        cd24ConfigInputVoltageLimitLo         INTEGER,
        cd24ConfigInputVoltageLimitHi         INTEGER,
        cd24ConfigInputVoltageLimitHiHi       INTEGER,
        cd24ConfigOutputCurrentLimitLoLo      INTEGER,
        cd24ConfigOutputCurrentLimitLo        INTEGER,
        cd24ConfigOutputCurrentLimitHi        INTEGER,
        cd24ConfigOutputCurrentLimitHiHi      INTEGER
    }

    cd24ConfigNESlotWrite OBJECT-TYPE
        SYNTAX NESlotWriteValue
        ACCESS read-write
        STATUS mandatory
        DESCRIPTION "By writing this variable a slot can be assigned
            for devices that dont support hardware slot detection.
            Reading '-1' means that the slot position is NOT writable."
    ::= { cd24ConfigurationEntry 1 }

    cd24ConfigInputVoltageLimitLoLo OBJECT-TYPE
        SYNTAX  INTEGER
        ACCESS  read-write
        STATUS  mandatory
        DESCRIPTION
            "The input voltage low alarm limit in 0.1 Volt units"
    ::={ cd24ConfigurationEntry 2 }

    cd24ConfigInputVoltageLimitLo OBJECT-TYPE
        SYNTAX  INTEGER
        ACCESS  read-write
        STATUS  mandatory
        DESCRIPTION
            "The input voltage low warning limit in 0.1 Volt units"
    ::={ cd24ConfigurationEntry 3 }

    cd24ConfigInputVoltageLimitHi OBJECT-TYPE
        SYNTAX  INTEGER
        ACCESS  read-write
        STATUS  mandatory
        DESCRIPTION
            "The input voltage high warning limit in 0.1 Volt units"
    ::={ cd24ConfigurationEntry 4 }

    cd24ConfigInputVoltageLimitHiHi OBJECT-TYPE
        SYNTAX  INTEGER
        ACCESS  read-write
        STATUS  mandatory
        DESCRIPTION
            "The input voltage high alarm limit in 0.1 Volt units"
    ::={ cd24ConfigurationEntry 5 }

    cd24ConfigOutputCurrentLimitLoLo OBJECT-TYPE
        SYNTAX  INTEGER
        ACCESS  read-write
        STATUS  mandatory
        DESCRIPTION
            "The output current low alarm limit in mA units"
    ::={ cd24ConfigurationEntry 6 }

    cd24ConfigOutputCurrentLimitLo OBJECT-TYPE
        SYNTAX  INTEGER
        ACCESS  read-write
        STATUS  mandatory
        DESCRIPTION
            "The output current low warning limit in mA units"
    ::={ cd24ConfigurationEntry 7 }

    cd24ConfigOutputCurrentLimitHi OBJECT-TYPE
        SYNTAX  INTEGER
        ACCESS  read-write
        STATUS  mandatory
        DESCRIPTION
            "The output current high warning limit in mA units"
    ::={ cd24ConfigurationEntry 8 }

    cd24ConfigOutputCurrentLimitHiHi OBJECT-TYPE
        SYNTAX  INTEGER
        ACCESS  read-write
        STATUS  mandatory
        DESCRIPTION
            "The output current high alarm limit in mA units"
    ::={ cd24ConfigurationEntry 9 }

--*****************************************************************************************
-- Display group




--*****************************************************************************************
END
