--- ****************************************************************************
-- *
-- * Description:   Implements definitions for the Ops-modul
-- *                (Optical Switch design release V01)
-- *
-- * Copyright 2003 by BKtel communications GmbH
-- *
-- *     V.0.1 07.05.03  M. Heldmann    first draft
-- *     V.0.2 23.07.03  M. Heldmann    added descriptions for the states
-- *     V.0.3 04.10.06  M. Heldmann    NESlotWriteValue expanded due to new 2G6 platform needs
-- *     V.0.4 29.05.08  M. Heldmann    renamed threshold parameters in xxxxMeasuringValuesTable
-- *     V.0.5 11.07.13  M. Heldmann    adjusted syntax of "CommonEntry" to remove MIB compiler warnings
-- *     V.0.5 05.09.14  M. Heldmann    changed CommonModuleWidth and ConfigNESlotWrite STATUS to optional
-- ****************************************************************************

BKTEL-HFC862-OPS-V01-MIB DEFINITIONS ::= BEGIN

    IMPORTS
        experimental, enterprises, TimeTicks, IpAddress, Counter
                 FROM RFC1155-SMI
    OBJECT-TYPE
                 FROM RFC-1212
        TRAP-TYPE
                 FROM RFC-1215
        modules, DisplayString, TruthValue, PerceivedSeverityValue, NESlotValue, ModuleWidthValue
                 FROM   BKTEL-HFC862-BASE-MIB
    ;

    ops                 OBJECT IDENTIFIER ::= { modules 105 }
    opsCommon           OBJECT IDENTIFIER ::= { ops 1 }
    opsStates           OBJECT IDENTIFIER ::= { ops 2 }
    opsConfiguration    OBJECT IDENTIFIER ::= { ops 3 }
    opsControl          OBJECT IDENTIFIER ::= { ops 4 }
    opsMeasuringValues  OBJECT IDENTIFIER ::= { ops 5 }
--  opsDisplay          OBJECT IDENTIFIER ::= { ops 6 }


--
-- Type definitions
--

        SwitchPosition ::= INTEGER
            {
            positionNominal(1),
            positionRedundant(2)
            }

        SwitchMode ::= INTEGER
            {
            modeManual(1),
            modeRevertive(2),
            modeNonRevertive(3)
            }

        NESlotWriteValue ::= INTEGER (-1..99)


--*****************************************************************************************
-- OPS ( Optical Switch with design release V01 )

--*****************************************************************************************
-- opsCommon group

    opsCommonNumberOfModules OBJECT-TYPE
        SYNTAX  INTEGER(0..50)
        ACCESS  read-only
        STATUS  mandatory
        DESCRIPTION "Number of modules in table."
  ::= { opsCommon 1 }

    opsCommonTable OBJECT-TYPE
        SYNTAX SEQUENCE OF OpsCommonEntry
        ACCESS not-accessible
        STATUS mandatory
        DESCRIPTION "The table contains all modules of the OPS-type in the NE"
  ::= { opsCommon 2 }

-- table of states entry(ro/rw)

    opsCommonEntry OBJECT-TYPE
        SYNTAX OpsCommonEntry
        ACCESS not-accessible
        STATUS mandatory
        DESCRIPTION "Common-Values for a module."
        INDEX { opsNESlot }
  ::= { opsCommonTable 1 }

-- the structure of the entry

    OpsCommonEntry ::= SEQUENCE
    {
        opsNESlot                      NESlotValue,
        opsCommonType                  DisplayString,
        opsCommonDescr                 DisplayString,
        opsCommonFirmwareId            DisplayString,
        opsCommonModuleWidth           ModuleWidthValue
    }

    opsNESlot OBJECT-TYPE
        SYNTAX  NESlotValue
        ACCESS  read-only
        STATUS  mandatory
        DESCRIPTION
        "The slot number of the chassis for which this
        entry contains management information."
    ::= { opsCommonEntry 1 }

    opsCommonType OBJECT-TYPE
        SYNTAX  DisplayString  (SIZE(0..32))
        ACCESS  read-only
        STATUS  mandatory
        DESCRIPTION
        "The type of physical module. modSlotEmpty indicates
         an empty slot.  A Value of modSlotUnknown indicates
         that the type of module is unknown."
    ::= { opsCommonEntry 2 }

    opsCommonDescr OBJECT-TYPE
        SYNTAX  DisplayString
        ACCESS  read-write
        STATUS  mandatory
        DESCRIPTION
        "A textual description of the module.
        If not available, this Value should be
        set to a zero length string."
    ::= { opsCommonEntry 3 }

    opsCommonFirmwareId OBJECT-TYPE
        SYNTAX DisplayString (SIZE(0..32))
        ACCESS read-only
        STATUS mandatory
        DESCRIPTION "The firmware Id of the module."
    ::= { opsCommonEntry 4 }

    opsCommonModuleWidth OBJECT-TYPE
        SYNTAX ModuleWidthValue
        ACCESS read-only
        STATUS optional
        DESCRIPTION "The width of the module in multiples of slots (1, 2, ...)"
    ::= {  opsCommonEntry 5  }

--*****************************************************************************************
-- opsMeasuringValues group

-- table of measuring Values

    opsMeasuringValuesTable OBJECT-TYPE
        SYNTAX SEQUENCE OF OpsMeasuringValuesEntry
        ACCESS not-accessible
        STATUS mandatory
        DESCRIPTION ""
   ::= { opsMeasuringValues 1 }

-- table of measuring Values entry

    opsMeasuringValuesEntry OBJECT-TYPE
        SYNTAX OpsMeasuringValuesEntry
        ACCESS not-accessible
        STATUS mandatory
        DESCRIPTION "Common-Values for a module."
        INDEX { opsNESlot }
  ::= { opsMeasuringValuesTable 1 }

--  the structure of the entry

    OpsMeasuringValuesEntry ::= SEQUENCE
    {
        opsInputPowerNominalLoLo          INTEGER,
        opsInputPowerNominalLo            INTEGER,
        opsInputPowerNominalValue         INTEGER,
        opsInputPowerNominalHi            INTEGER,
        opsInputPowerNominalHiHi          INTEGER,

        opsInputPowerRedundantLoLo        INTEGER,
        opsInputPowerRedundantLo          INTEGER,
        opsInputPowerRedundantValue       INTEGER,
        opsInputPowerRedundantHi          INTEGER,
        opsInputPowerRedundantHiHi        INTEGER,

        opsTemperatureLoLo                INTEGER,
        opsTemperatureLo                  INTEGER,
        opsTemperatureValue               INTEGER,
        opsTemperatureHi                  INTEGER,
        opsTemperatureHiHi                INTEGER
    }

-- *****
    opsInputPowerNominalLoLo OBJECT-TYPE
        SYNTAX INTEGER
        ACCESS read-only
        STATUS mandatory
        DESCRIPTION "Input power (nominal channel) low alarm threshold in steps of 0.1dBm."
    ::= { opsMeasuringValuesEntry 1 }

    opsInputPowerNominalLo OBJECT-TYPE
        SYNTAX INTEGER
        ACCESS read-only
        STATUS mandatory
        DESCRIPTION "Input power (nominal channel) low warning threshold in steps of 0.1dBm."
    ::= { opsMeasuringValuesEntry 2 }

    opsInputPowerNominalValue OBJECT-TYPE
        SYNTAX INTEGER
        ACCESS read-only
        STATUS mandatory
        DESCRIPTION "Input power (nominal channel) in steps of 0.1dBm."
    ::= { opsMeasuringValuesEntry 3 }

    opsInputPowerNominalHi OBJECT-TYPE
        SYNTAX INTEGER
        ACCESS read-only
        STATUS mandatory
        DESCRIPTION "Input power (nominal channel) high warning threshold in steps of 0.1dBm."
    ::= { opsMeasuringValuesEntry 4 }

    opsInputPowerNominalHiHi OBJECT-TYPE
        SYNTAX INTEGER
        ACCESS read-only
        STATUS mandatory
        DESCRIPTION "Input power (nominal channel) high alarm threshold in steps of 0.1dBm."
    ::= { opsMeasuringValuesEntry 5 }

-- *****
    opsInputPowerRedundantLoLo OBJECT-TYPE
        SYNTAX INTEGER
        ACCESS read-only
        STATUS mandatory
        DESCRIPTION "Input power (redundant channel) low alarm threshold in steps of 0.1dBm."
    ::= { opsMeasuringValuesEntry 6 }

    opsInputPowerRedundantLo OBJECT-TYPE
        SYNTAX INTEGER
        ACCESS read-only
        STATUS mandatory
        DESCRIPTION "Input power (redundant channel) low warning threshold in steps of 0.1dBm."
    ::= { opsMeasuringValuesEntry 7 }

    opsInputPowerRedundantValue OBJECT-TYPE
        SYNTAX INTEGER
        ACCESS read-only
        STATUS mandatory
        DESCRIPTION "Input power (redundant channel) in steps of 0.1dBm."
    ::= { opsMeasuringValuesEntry 8 }

    opsInputPowerRedundantHi OBJECT-TYPE
        SYNTAX INTEGER
        ACCESS read-only
        STATUS mandatory
        DESCRIPTION "Input power (redundant channel) high warning threshold in steps of 0.1dBm."
    ::= { opsMeasuringValuesEntry 9 }

    opsInputPowerRedundantHiHi OBJECT-TYPE
        SYNTAX INTEGER
        ACCESS read-only
        STATUS mandatory
        DESCRIPTION "Input power (redundant channel) high alarm threshold in steps of 0.1dBm."
    ::= { opsMeasuringValuesEntry 10 }

-- *****
    opsTemperatureLoLo OBJECT-TYPE
        SYNTAX INTEGER
        ACCESS read-only
        STATUS mandatory
        DESCRIPTION "The module temperature low alarm threshold in steps of 0.1 celsius degrees."
    ::= { opsMeasuringValuesEntry 11 }

    opsTemperatureLo OBJECT-TYPE
        SYNTAX INTEGER
        ACCESS read-only
        STATUS mandatory
        DESCRIPTION "The module temperature low warning threshold in steps of 0.1 celsius degrees."
    ::= { opsMeasuringValuesEntry 12 }

    opsTemperatureValue OBJECT-TYPE
        SYNTAX INTEGER
        ACCESS read-only
        STATUS mandatory
        DESCRIPTION "The module temperature in steps of 0.1 celsius degrees."
    ::= { opsMeasuringValuesEntry 13 }

    opsTemperatureHi OBJECT-TYPE
        SYNTAX INTEGER
        ACCESS read-only
        STATUS mandatory
        DESCRIPTION "The module temperature high warning threshold in steps of 0.1 celsius degrees."
    ::= { opsMeasuringValuesEntry 14 }

    opsTemperatureHiHi OBJECT-TYPE
        SYNTAX INTEGER
        ACCESS read-only
        STATUS mandatory
        DESCRIPTION "The module temperature high alarm threshold in steps of 0.1 celsius degrees."
    ::= { opsMeasuringValuesEntry 15 }


--*****************************************************************************************
--  opsStates group

-- Note: For every control OId there must be a correspondant alarm OId!

    opsStatesTable OBJECT-TYPE
        SYNTAX SEQUENCE OF OpsStatesEntry
        ACCESS not-accessible
        STATUS mandatory
        DESCRIPTION ""
    ::= { opsStates 1 }

-- table of states entry(ro/rw)

    opsStatesEntry OBJECT-TYPE
        SYNTAX OpsStatesEntry
        ACCESS not-accessible
        STATUS mandatory
        DESCRIPTION "Alarms for a module."
        INDEX { opsNESlot }
    ::= { opsStatesTable 1 }

-- the structure of the entry

    OpsStatesEntry ::= SEQUENCE
    {
        opsStatesInputNominalLow      PerceivedSeverityValue,
        opsStatesInputNominalHigh     PerceivedSeverityValue,
        opsStatesInputRedundantLow    PerceivedSeverityValue,
        opsStatesInputRedundantHigh   PerceivedSeverityValue,
        opsStatesSwitchedToRedundant  PerceivedSeverityValue,
        opsStatesManualMode           PerceivedSeverityValue,
        opsStatesBootloader           PerceivedSeverityValue,
        opsStatesDefective            PerceivedSeverityValue
    }

    opsStatesInputNominalLow OBJECT-TYPE
        SYNTAX PerceivedSeverityValue
        ACCESS read-only
        STATUS mandatory
        DESCRIPTION "Optical input power (nominal input) low"
    ::= { opsStatesEntry 1 }

    opsStatesInputNominalHigh OBJECT-TYPE
        SYNTAX PerceivedSeverityValue
        ACCESS read-only
        STATUS mandatory
        DESCRIPTION "Optical input power (nominal input) high"
    ::= { opsStatesEntry 2 }

    opsStatesInputRedundantLow OBJECT-TYPE
        SYNTAX PerceivedSeverityValue
        ACCESS read-only
        STATUS mandatory
        DESCRIPTION "Optical input power (redundant input) low"
    ::= { opsStatesEntry 3 }

    opsStatesInputRedundantHigh OBJECT-TYPE
        SYNTAX PerceivedSeverityValue
        ACCESS read-only
        STATUS mandatory
        DESCRIPTION "Optical input power (redundant input) high"
    ::= { opsStatesEntry 4 }

    opsStatesSwitchedToRedundant OBJECT-TYPE
        SYNTAX PerceivedSeverityValue
        ACCESS read-only
        STATUS mandatory
        DESCRIPTION "The optical switch position has changed to the redundant input"
    ::= { opsStatesEntry 5 }

    opsStatesManualMode OBJECT-TYPE
        SYNTAX PerceivedSeverityValue
        ACCESS read-only
        STATUS mandatory
        DESCRIPTION "The optical switch runs in manual (non automatic) mode"
    ::= { opsStatesEntry 6 }

    opsStatesBootloader OBJECT-TYPE
        SYNTAX PerceivedSeverityValue
        ACCESS read-only
        STATUS mandatory
        DESCRIPTION 
            "The device is running in bootloader mode 
             without a legal application software." 
    ::= { opsStatesEntry 7 }

    opsStatesDefective OBJECT-TYPE
        SYNTAX PerceivedSeverityValue
        ACCESS read-only
        STATUS mandatory
        DESCRIPTION
            "The NEC has lost the connection to the device. 
             Reason may be a removed or defective device.
             Note that this state is set by the NEC and not 
             by the device" 
    ::= { opsStatesEntry 8 }


--*****************************************************************************************
--  opsControl group

  opsControlTable OBJECT-TYPE
    SYNTAX SEQUENCE OF OpsControlEntry
    ACCESS not-accessible
    STATUS mandatory
    DESCRIPTION ""
  ::= { opsControl 1 }

-- table of control entry(ro/rw)

  opsControlEntry OBJECT-TYPE
    SYNTAX OpsControlEntry
    ACCESS not-accessible
    STATUS mandatory
    DESCRIPTION "Alarms for a module."
    INDEX { opsNESlot }
  ::= { opsControlTable 1 }

-- the structure of the entry

    OpsControlEntry ::= SEQUENCE
    {
        opsControlPosition          SwitchPosition,
        opsControlReset             TruthValue,
        opsControlModuleLedBlink    TruthValue
    }

    opsControlPosition OBJECT-TYPE
        SYNTAX SwitchPosition
        ACCESS read-write
        STATUS mandatory
        DESCRIPTION
            "The actual position of the switch
             !!! This parameter is only writable if opsConfigMode == modeManual(1) !!!"
    ::={ opsControlEntry 1 }

    opsControlReset OBJECT-TYPE
      SYNTAX TruthValue
      ACCESS read-write
      STATUS mandatory
      DESCRIPTION "Reset the module."
    ::= { opsControlEntry 2 }

    opsControlModuleLedBlink OBJECT-TYPE
        SYNTAX TruthValue
        ACCESS read-write
        STATUS mandatory
        DESCRIPTION   "Writing this variable to true(1) lets the device's 
        modul LED blink green for 10 seconds. 
        Writing this variable to false(2) stops blinking at once.
        This variable always returns false(2) on read requests"
    ::= { opsControlEntry 3 }


--*****************************************************************************************
-- opsConfiguration group

    opsConfigurationTable OBJECT-TYPE
        SYNTAX SEQUENCE OF OpsConfigurationEntry
        ACCESS not-accessible
        STATUS mandatory
        DESCRIPTION ""
    ::= { opsConfiguration 1 }

-- table of configuration entry(ro/rw)

    opsConfigurationEntry OBJECT-TYPE
        SYNTAX OpsConfigurationEntry
        ACCESS not-accessible
        STATUS mandatory
        DESCRIPTION ""
        INDEX { opsNESlot  }
    ::= { opsConfigurationTable 1 }

-- the structure of the entry

    OpsConfigurationEntry ::= SEQUENCE
    {
        opsConfigNESlotWrite                 NESlotWriteValue,
        opsConfigMode                        SwitchMode,
        opsConfigFallbackTime                INTEGER,
        opsConfigInputPwrNominalLimitLoLo    INTEGER,
        opsConfigInputPwrNominalLimitLo      INTEGER,
        opsConfigInputPwrNominalLimitHi      INTEGER,
        opsConfigInputPwrNominalLimitHiHi    INTEGER,
        opsConfigInputPwrRedundantLimitLoLo  INTEGER,
        opsConfigInputPwrRedundantLimitLo    INTEGER,
        opsConfigInputPwrRedundantLimitHi    INTEGER,
        opsConfigInputPwrRedundantLimitHiHi  INTEGER
    }

    opsConfigNESlotWrite OBJECT-TYPE
        SYNTAX NESlotWriteValue
        ACCESS read-write
        STATUS optional
        DESCRIPTION "By writing this variable a slot can be assigned
            for devices that dont support hardware slot detection.
            Reading '-1' means that the slot position is NOT writable."
    ::= { opsConfigurationEntry 1 }

    opsConfigMode OBJECT-TYPE
        SYNTAX SwitchMode
        ACCESS read-write
        STATUS mandatory
        DESCRIPTION
            "The mode of the switch"
    ::={ opsConfigurationEntry 2 }

    opsConfigFallbackTime OBJECT-TYPE
        SYNTAX  INTEGER (30..300)
        ACCESS  read-write
        STATUS  mandatory
        DESCRIPTION
            "Delay in seconds (30 ... 300sec) before automatically
             switching back from the redundant to the nominal channel 
             in revertive mode [opsConfigMode == modeRevertive(2)]"
    ::={ opsConfigurationEntry 3 }

    opsConfigInputPwrNominalLimitLoLo OBJECT-TYPE
        SYNTAX  INTEGER
        ACCESS  read-write
        STATUS  mandatory
        DESCRIPTION
            "The nominal channel's optical input power low alarm limit in 0.1 dBm units.
             THIS LIMIT IS THE DETECTION LEVEL USED FOR AUTOMATIC SWITCHING"
    ::={ opsConfigurationEntry 4 }

    opsConfigInputPwrNominalLimitLo OBJECT-TYPE
        SYNTAX  INTEGER
        ACCESS  read-write
        STATUS  mandatory
        DESCRIPTION
            "The nominal channel's optical input power low warning limit in 0.1 dBm units"
    ::={ opsConfigurationEntry 5 }

    opsConfigInputPwrNominalLimitHi OBJECT-TYPE
        SYNTAX  INTEGER
        ACCESS  read-write
        STATUS  mandatory
        DESCRIPTION
            "The nominal channel's optical input power high warning limit in 0.1 dBm units"
    ::={ opsConfigurationEntry 6 }

    opsConfigInputPwrNominalLimitHiHi OBJECT-TYPE
        SYNTAX  INTEGER
        ACCESS  read-write
        STATUS  mandatory
        DESCRIPTION
            "The nominal channel's optical input power high alarm limit in 0.1 dBm units"
    ::={ opsConfigurationEntry 7 }

    opsConfigInputPwrRedundantLimitLoLo OBJECT-TYPE
        SYNTAX  INTEGER
        ACCESS  read-write
        STATUS  mandatory
        DESCRIPTION
            "The redundant channel's optical input power low alarm limit in 0.1 dBm units.
             THIS LIMIT IS THE DETECTION LEVEL USED FOR AUTOMATIC SWITCHING"
    ::={ opsConfigurationEntry 8 }

    opsConfigInputPwrRedundantLimitLo OBJECT-TYPE
        SYNTAX  INTEGER
        ACCESS  read-write
        STATUS  mandatory
        DESCRIPTION
            "The redundant channel's optical input power low warning limit in 0.1 dBm units"
    ::={ opsConfigurationEntry 9 }

    opsConfigInputPwrRedundantLimitHi OBJECT-TYPE
        SYNTAX  INTEGER
        ACCESS  read-write
        STATUS  mandatory
        DESCRIPTION
            "The redundant channel's optical input power high warning limit in 0.1 dBm units"
    ::={ opsConfigurationEntry 10 }

    opsConfigInputPwrRedundantLimitHiHi OBJECT-TYPE
        SYNTAX  INTEGER
        ACCESS  read-write
        STATUS  mandatory
        DESCRIPTION
            "The redundant channel's optical input power high alarm limit in 0.1 dBm units"
    ::={ opsConfigurationEntry 11 }


--*****************************************************************************************
-- Display group



--*****************************************************************************************
END
